-- ****************************************************************************
-- HP NSA System Information MIB
-- September 7, 1994
--
-- Copyright Hewlett-Packard Company 1994.
-- All rights reserved.
--
-- The information in this document is subject to change without notice.
--
-- The HP enterprise number is 11. The ASN.1 prefix to, and including,
-- the HP enterprise ID is 1.3.6.1.4.1.11.
--
-- ****************************************************************************
-- Summary of HP NSA System Information MIB
-- ****************************************************************************
-- hp                                              (1.3.6.1.4.1.11)
--    nm                                           (hp.2)
--       hpnsa                                     (nm.23)
--          hpnsaSystemInfo Group                  (hpnsa.7)
--             hpnsaSiMibRev Group                 (hpnsa.7.1)
--                hpnsaSiMibRevMajor               (hpnsa.7.1.1)
--                hpnsaSiMibRevMinor               (hpnsa.7.1.2)
--             hpnsaSiAgent Group                  (hpnsa.7.2)
--                hpnsaSiAgentTable                (hpnsa.7.2.1)
--                   hpnsaSiAgentEntry             (hpnsa.7.2.1.1)
--                      hpnsaSiAgentIndex          (hpnsa.7.2.1.1.1)
--                      hpnsaSiAgentName           (hpnsa.7.2.1.1.2)
--                      hpnsaSiAgentVersion        (hpnsa.7.2.1.1.3)
--                      hpnsaSiAgentDate           (hpnsa.7.2.1.1.4)
--             hpnsaSiBasicInfo Group              (hpnsa.7.3)
--                hpnsaSiModel                     (hpnsa.7.3.1)
--                hpnsaSiBIOSVersion               (hpnsa.7.3.2)
--                hpnsaSiVideoBIOSVersion          (hpnsa.7.3.3)
--                hpnsaSiSCSIBIOSVersion           (hpnsa.7.3.4)
--                hpnsaSiNumEISASlots              (hpnsa.7.3.5)
--                hpnsaSiNumPCISlots               (hpnsa.7.3.6)
--                hpnsaSiNumCPU                    (hpnsa.7.3.7)
--                hpnsaSiCPUTable                  (hpnsa.7.3.8)
--                   hpnsaSiCPUEntry               (hpnsa.7.3.8.1)
--                      hpnsaSiCPUIndex            (hpnsa.7.3.8.1.1)
--                      hpnsaSiCPUModel            (hpnsa.7.3.8.1.2)
--                      hpnsaSiCPUSpeed            (hpnsa.7.3.8.1.3)
--                hpnsaSiOpSysType                 (hpnsa.7.3.9)
--                hpnsaSiOpSysVer                  (hpnsa.7.3.10)
--                hpnsaSiSystemName                (hpnsa.7.3.11)
--                hpnsaSiSystemID                  (hpnsa.7.3.12)
--                hpnsaSiKbdType                   (hpnsa.7.3.13)
--                hpnsaSiMouseType                 (hpnsa.7.3.14)
--                hpnsaSiVideoType                 (hpnsa.7.3.15)
--                hpnsaSiNumISASlots               (hpnsa.7.3.16)
--             hpnsaSiSecurity Group               (hpnsa.7.4)
--                hpnsaSiPowerOnPassword           (hpnsa.7.4.1)
--                hpnsaSiNetServerMode             (hpnsa.7.4.2)
--                hpnsaSiKeyboardLockPassword      (hpnsa.7.4.3)
--                hpnsaSiVideoBlankMode            (hpnsa.7.4.4)
--                hpnsaSiBootDiskPriority          (hpnsa.7.4.5)
--                hpnsaSiWriteToFloppy             (hpnsa.7.4.6)
--                hpnsaSiKbdMouseInactivityTO      (hpnsa.7.4.7)
--             hpnsaSiPort Group                   (hpnsa.7.5)
--                hpnsaSiPortTable                 (hpnsa.7.5.1)
--                   hpnsaSiPortEntry              (hpnsa.7.5.1.1)
--                      hpnsaSiPortIndex           (hpnsa.7.5.1.1.1)
--                      hpnsaSiPortType            (hpnsa.7.5.1.1.2)
--                      hpnsaSiPortStartAddress    (hpnsa.7.5.1.1.3)
--                      hpnsaSiPortEndAddress      (hpnsa.7.5.1.1.4)
--                      hpnsaSiPortInterruptNum    (hpnsa.7.5.1.1.5)
--             hpnsaSiMemory Group                 (hpnsa.7.6)
--                hpnsaSiBaseMemSize               (hpnsa.7.6.1)
--                hpnsaSiExtMemSize                (hpnsa.7.6.2)
--                hpnsaSiMemType                   (hpnsa.7.6.3)
--                hpnsaSiMemSpeed                  (hpnsa.7.6.4)
--             hpnsaSiHardDisk Group               (hpnsa.7.7)
--                hpnsaSiNumHardDisks              (hpnsa.7.7.1)
--                hpnsaSiHardDiskTable             (hpnsa.7.7.2)
--                   hpnsaSiHardDiskEntry          (hpnsa.7.7.2.1)
--                      hpnsaSiHardDiskIndex       (hpnsa.7.7.2.1.1)
--                      hpnsaSiHardDiskType        (hpnsa.7.7.2.1.2)
--                      hpnsaSiHardDiskCylinders   (hpnsa.7.7.2.1.3)
--                      hpnsaSiHardDiskSectors     (hpnsa.7.7.2.1.4)
--                      hpnsaSiHardDiskHeads       (hpnsa.7.7.2.1.5)
--                      hpnsaSiHardDiskCapacity    (hpnsa.7.7.2.1.6)
--             hpnsaSiFloppyDrive Group            (hpnsa.7.8)
--                hpnsaSiNumFloppyDrives           (hpnsa.7.8.1)
--                hpnsaSiFloppyDriveTable          (hpnsa.7.8.2)
--                   hpnsaSiFloppyDriveEntry       (hpnsa.7.8.2.1)
--                      hpnsaSiFloppyDriveIndex    (hpnsa.7.8.2.1.1)
--                      hpnsaSiFloppyDriveType     (hpnsa.7.8.2.1.2)
--
-- ****************************************************************************

HPNSASINFO-MIB DEFINITIONS ::= BEGIN
   IMPORTS
      enterprises    FROM RFC1155-SMI
      DisplayString  FROM RFC1213-MIB
      OBJECT-TYPE    FROM RFC-1212;

   hp                    OBJECT IDENTIFIER ::= { enterprises 11 }
   nm                    OBJECT IDENTIFIER ::= { hp 2 }
   hpnsa                 OBJECT IDENTIFIER ::= { nm 23 }
   hpnsaSystemInfo       OBJECT IDENTIFIER ::= { hpnsa 7 }
   hpnsaSiMibRev         OBJECT IDENTIFIER ::= { hpnsaSystemInfo 1 }
   hpnsaSiAgent          OBJECT IDENTIFIER ::= { hpnsaSystemInfo 2 }
   hpnsaSiBasicInfo      OBJECT IDENTIFIER ::= { hpnsaSystemInfo 3 }
   hpnsaSiSecurity       OBJECT IDENTIFIER ::= { hpnsaSystemInfo 4 }
   hpnsaSiPort           OBJECT IDENTIFIER ::= { hpnsaSystemInfo 5 }
   hpnsaSiMemory         OBJECT IDENTIFIER ::= { hpnsaSystemInfo 6 }
   hpnsaSiHardDisk       OBJECT IDENTIFIER ::= { hpnsaSystemInfo 7 }
   hpnsaSiFloppyDrive    OBJECT IDENTIFIER ::= { hpnsaSystemInfo 8 }

-- ****************************************************************************
-- HP NSA System Information MIB Revision
-- ======================================
--
-- hp                                              (1.3.6.1.4.1.11)
--    nm                                           (hp.2)
--       hpnsa                                     (nm.23)
--          hpnsaSystemInfo Group                  (hpnsa.7)
--             hpnsaSiMibRev Group                 (hpnsa.7.1)
--                hpnsaSiMibRevMajor               (hpnsa.7.1.1)
--                hpnsaSiMibRevMinor               (hpnsa.7.1.2)
--
-- Implementation of the MibRev group is mandatory for all HPNSA Agents
-- supporting the HP NSA System Information MIB.
--
-- An HPNSA Agent conforming to this document will return a
-- hpnsaSiMibRevMajor of 1 and a hpnsaSiMibRevMinor of 0.
--
-- ****************************************************************************

   hpnsaSiMibRevMajor OBJECT-TYPE
      SYNTAX INTEGER (1..65535)
      ACCESS read-only
      STATUS mandatory
      DESCRIPTION
	 "The major revision level of the MIB."
   ::= { hpnsaSiMibRev 1 }

   hpnsaSiMibRevMinor OBJECT-TYPE
      SYNTAX INTEGER (0..65535)
      ACCESS read-only
      STATUS mandatory
      DESCRIPTION
	 "The minor revision level of the MIB."
   ::= { hpnsaSiMibRev 2 }

-- ****************************************************************************
-- HP NSA System Information Agent Information
-- ===========================================
--
-- hp                                              (1.3.6.1.4.1.11)
--    nm                                           (hp.2)
--       hpnsa                                     (nm.23)
--          hpnsaSystemInfo Group                  (hpnsa.7)
--             hpnsaSiAgent Group                  (hpnsa.7.2)
--                hpnsaSiAgentTable                (hpnsa.7.2.1)
--                   hpnsaSiAgentEntry             (hpnsa.7.2.1.1)
--                      hpnsaSiAgentIndex          (hpnsa.7.2.1.1.1)
--                      hpnsaSiAgentName           (hpnsa.7.2.1.1.2)
--                      hpnsaSiAgentVersion        (hpnsa.7.2.1.1.3)
--                      hpnsaSiAgentDate           (hpnsa.7.2.1.1.4)
--
--  Implementation of the hpnsaSiAgent group is mandatory for all
--  HPNSA Agents that support the System Information MIB.
--
-- ****************************************************************************
-- HP NSA System Information Agent Table
-- ****************************************************************************

   hpnsaSiAgentTable OBJECT-TYPE
      SYNTAX SEQUENCE OF HPnsaSiAgentEntry
      ACCESS not-accessible
      STATUS mandatory
      DESCRIPTION
	 "A table of software modules that provide an interface to the
	 device this MIB describes."
   ::= { hpnsaSiAgent 1 }

   hpnsaSiAgentEntry OBJECT-TYPE
      SYNTAX HPnsaSiAgentEntry
      ACCESS not-accessible
      STATUS mandatory
      DESCRIPTION
	 "A description of the Agents that access system information."
      INDEX { hpnsaSiAgentIndex }
   ::= { hpnsaSiAgentTable 1 }

   HPnsaSiAgentEntry ::= SEQUENCE {
      hpnsaSiAgentIndex       INTEGER,
      hpnsaSiAgentName        DisplayString,
      hpnsaSiAgentVersion     DisplayString,
      hpnsaSiAgentDate        OCTET STRING
   }

   hpnsaSiAgentIndex OBJECT-TYPE
      SYNTAX INTEGER (0..255)
      ACCESS read-only
      STATUS mandatory
      DESCRIPTION
	 "A unique index for this agent."
   ::= { hpnsaSiAgentEntry 1 }

   hpnsaSiAgentName OBJECT-TYPE
      SYNTAX DisplayString (SIZE (0..255))
      ACCESS read-only
      STATUS mandatory
      DESCRIPTION
	 "Name of the agent/agents satisfying SNMP requests for this MIB."
    ::= { hpnsaSiAgentEntry 2 }

   hpnsaSiAgentVersion OBJECT-TYPE
      SYNTAX DisplayString (SIZE (0..10))
      ACCESS read-only
      STATUS mandatory
      DESCRIPTION
	 "Version number of the agent/agents satisfying SNMP requests for
	 this MIB."
   ::= { hpnsaSiAgentEntry 3 }

   hpnsaSiAgentDate OBJECT-TYPE
      SYNTAX OCTET STRING (SIZE (7))
      ACCESS read-only
      STATUS mandatory
      DESCRIPTION
	 "The date on which this agent was created.

	 field  octets  contents                  range
	 _________________________________________________
	    1       1    years since 1900          0..255
	    2       2    month                     1..12
	    3       3    day                       1..31
	    4       4    hour                      0..23
	    5       5    minute                    0..59
	    6       6    second                    0..59"
   ::= { hpnsaSiAgentEntry 4 }

-- ****************************************************************************
-- HP NSA System Information Basic Info Group
-- ==========================================
--
-- hp                                              (1.3.6.1.4.1.11)
--    nm                                           (hp.2)
--       hpnsa                                     (nm.23)
--          hpnsaSystemInfo Group                  (hpnsa.7)
--             hpnsaSiBasicInfo Group              (hpnsa.7.3)
--                hpnsaSiModel                     (hpnsa.7.3.1)
--                hpnsaSiBIOSVersion               (hpnsa.7.3.2)
--                hpnsaSiVideoBIOSVersion          (hpnsa.7.3.3)
--                hpnsaSiSCSIBIOSVersion           (hpnsa.7.3.4)
--                hpnsaSiNumEISASlots              (hpnsa.7.3.5)
--                hpnsaSiNumPCISlots               (hpnsa.7.3.6)
--                hpnsaSiNumCPU                    (hpnsa.7.3.7)
--                hpnsaSiCPUTable                  (hpnsa.7.3.8)
--                   hpnsaSiCPUEntry               (hpnsa.7.3.8.1)
--                      hpnsaSiCPUIndex            (hpnsa.7.3.8.1.1)
--                      hpnsaSiCPUModel            (hpnsa.7.3.8.1.2)
--                      hpnsaSiCPUSpeed            (hpnsa.7.3.8.1.3)
--                hpnsaSiOpSysType                 (hpnsa.7.3.9)
--                hpnsaSiOpSysVer                  (hpnsa.7.3.10)
--                hpnsaSiSystemName                (hpnsa.7.3.11)
--                hpnsaSiSystemID                  (hpnsa.7.3.12)
--                hpnsaSiKbdType                   (hpnsa.7.3.13)
--                hpnsaSiMouseType                 (hpnsa.7.3.14)
--                hpnsaSiVideoType                 (hpnsa.7.3.15)
--
-- The hpnsaSiSystemInfo group contains system specific information.
--
-- ****************************************************************************

   hpnsaSiModel OBJECT-TYPE
      SYNTAX INTEGER {
	hpVectraPC(0),
	hpVectraES-12-PC(1), 
	hpVectraRS-20-PC(2),
	hpVectraPortableCS-PC(3),
	hpVectraES-PC(4),
	hpVectraCS-PC(5),
	hpVectraRS-16-PC(6), 
	hpVectraQS-16-PC(7), 
	hpVectraQS-20-PC(8), 
	hpVectraRS-20C-PC(9), 
	hpVectraRS-25C-PC(10), 
	hpVectraLS-286-PC(11), 
	hpVectraQS-16S-PC(12), 
	hpVectra386-25-PC(13), 
	hpVectra486-25T-PC(14), 
	hpVectra286-12-PC(15), 
	hpVectra486-33T-PC(16), 
	hpVectra386-20-PC(17), 
	hpVectra386-16N-PC(18), 
	hpVectra386-20N-PC(19), 
	hpVectra486s-20-PC(20), 
	hpVectra386s-20-PC(21), 
	hpVectra486-25U-PC(22), 
	hpVectra486-33U-PC(23), 
	hpVectra486-50U-PC(24), 
	hpVectra486-66U-PC(25), 
	hpVectra486-ST-Series(26),
	hpVectra386-25N(27),
	hpVectra486-N(28),
	hpVectra386s-25(29),
	hpVectra386-33N(30),
	hpVectra486-33N(32),
	hpNetServerLE-Series(35),
	hpNetServerLM-Series(36),
	hpNetServerLF-Series(40),
	hpNetServerLC-Series(41),
	hpNetServerLS-Series(42),
	hpNetServerLH-Series(43),
	hpNetServerLC-Series(44),
	hpNetServerLX-Series(46),
	hpNetServerLH-Series(47),
	hpNetServerLH-Series(49),
	hpNetServerE-Series(50),
	hpNetServerE-Series(51),
	hpNetServerLD-Series(52)
      }            
      ACCESS read-only
      STATUS mandatory
      DESCRIPTION
	 "System model"
   ::= { hpnsaSiBasicInfo 1 }

   hpnsaSiBIOSVersion OBJECT-TYPE
      SYNTAX DisplayString (SIZE (0..255))
      ACCESS read-only
      STATUS mandatory
      DESCRIPTION
	 "Version number of the system BIOS."
   ::= { hpnsaSiBasicInfo 2 }

   hpnsaSiVideoBIOSVersion OBJECT-TYPE
      SYNTAX DisplayString (SIZE (0..255))
      ACCESS read-only
      STATUS optional
      DESCRIPTION
	 "Version number of the video BIOS."
   ::= { hpnsaSiBasicInfo 3 }

   hpnsaSiSCSIBIOSVersion OBJECT-TYPE
      SYNTAX DisplayString (SIZE (0..255))
      ACCESS read-only
      STATUS mandatory
      DESCRIPTION
	 "Version number of the SCSI BIOS."
   ::= { hpnsaSiBasicInfo 4 }

   hpnsaSiNumEISASlots OBJECT-TYPE
      SYNTAX INTEGER
      ACCESS read-only
      STATUS mandatory
      DESCRIPTION
	 "Number of EISA slots in the system."
   ::= { hpnsaSiBasicInfo 5 }

   hpnsaSiNumPCISlots OBJECT-TYPE
      SYNTAX INTEGER
      ACCESS read-only
      STATUS mandatory
      DESCRIPTION
	 "Number of PCI slots in the system."
   ::= { hpnsaSiBasicInfo 6 }
   
   hpnsaSiNumCPU OBJECT-TYPE
      SYNTAX INTEGER
      ACCESS read-only
      STATUS mandatory
      DESCRIPTION
	 "Number of CPUs installed in the system."
   ::= { hpnsaSiBasicInfo 7 }

   hpnsaSiCPUTable OBJECT-TYPE
      SYNTAX SEQUENCE OF HPnsaSiCPUEntry
      ACCESS not-accessible
      STATUS mandatory
      DESCRIPTION
	 "A table of CPU types installed in the system."
   ::= { hpnsaSiBasicInfo 8 }

   hpnsaSiCPUEntry OBJECT-TYPE
      SYNTAX HPnsaSiCPUEntry
      ACCESS not-accessible
      STATUS mandatory
      DESCRIPTION
	 "A description of the CPUs installed in the system."
      INDEX { hpnsaSiCPUIndex }
   ::= { hpnsaSiCPUTable 1 }

   HPnsaSiCPUEntry ::= SEQUENCE {
      hpnsaSiCPUIndex   INTEGER,
      hpnsaSiCPUModel   INTEGER,
      hpnsaSiCPUSpeed   INTEGER
   }

   hpnsaSiCPUIndex OBJECT-TYPE
      SYNTAX INTEGER (0..255)
      ACCESS read-only
      STATUS mandatory
      DESCRIPTION
	 "A unique index for this CPU."
   ::= { hpnsaSiCPUEntry 1 }

   hpnsaSiCPUModel OBJECT-TYPE
      SYNTAX INTEGER {
	cpu-80286(0),
	cpu-8088(1),
	cpu-8086(2),
	cpu-80386(3),
	cpu-80386-SX(4),
	cpu-486-DX(5),
	cpu-486-SX(6),
	cpu-486-DX2-or-OverDrive(8),
	cpu-486-P23T(9),
	cpu-487-SX(10),
	cpu-Pentium(11),
	cpu-Pentium-OverDrive(12),
	cpu-486-24C(13),
	cpu-Pentium-Series-P54C(14),
	cpu-Pentium-Series-P54CT(15),
	cpu-Pentium-Series-P54CM(16),
	cpu-486-SX2(17),
	cpu-486-SL(18),
	cpu-Pentium-Series-P6(19),
	notPresent(253),
	cpu-Dual-Pentium(254),
	cpu-Unknown(255)
		}
		ACCESS read-only
		STATUS mandatory
		DESCRIPTION
			"CPU model"
	::= { hpnsaSiCPUEntry 2 }

	hpnsaSiCPUSpeed OBJECT-TYPE
		SYNTAX INTEGER
		ACCESS read-only
      STATUS mandatory
      DESCRIPTION
	 "CPU speed in MHz."
   ::= { hpnsaSiCPUEntry 3 }

   hpnsaSiOpSysType OBJECT-TYPE
      SYNTAX DisplayString (SIZE (0..255))
      ACCESS read-only
      STATUS mandatory
      DESCRIPTION
	 "Name of the operating system executing on this system,
	 e.g., Microsoft Windows NT, Novell NetWare, etc."
   ::= { hpnsaSiBasicInfo 9 }

   hpnsaSiOpSysVer OBJECT-TYPE
      SYNTAX DisplayString (SIZE (0..255))
      ACCESS read-only
      STATUS mandatory
      DESCRIPTION
	 "Operating system version number string., e.g., 3.1."
   ::= { hpnsaSiBasicInfo 10 }

   hpnsaSiSystemName OBJECT-TYPE
      SYNTAX DisplayString (SIZE (0..255))
      ACCESS read-only
      STATUS mandatory
      DESCRIPTION
	 "Network name of the system, e.g., PAPAYA."
   ::= { hpnsaSiBasicInfo 11 }

   hpnsaSiSystemID OBJECT-TYPE
      SYNTAX DisplayString (SIZE (0..255))
      ACCESS read-only
      STATUS optional
      DESCRIPTION
	 "System ID string that uniquely identifies the system."
   ::= { hpnsaSiBasicInfo 12 }

   hpnsaSiKbdType OBJECT-TYPE
      SYNTAX DisplayString (SIZE (0..255))
      ACCESS read-only
      STATUS optional
      DESCRIPTION
	 "Type of keyboard installed, e.g., U.S., French, German, etc."
   ::= { hpnsaSiBasicInfo 13 }

   hpnsaSiMouseType OBJECT-TYPE
      SYNTAX DisplayString (SIZE (0..255))
      ACCESS read-only
      STATUS optional
      DESCRIPTION
	 "Type of mouse installed, e.g., Microsoft or compatible, etc."
   ::= { hpnsaSiBasicInfo 14 }

   hpnsaSiVideoType OBJECT-TYPE
      SYNTAX DisplayString (SIZE (0..255))
      ACCESS read-only
      STATUS optional
      DESCRIPTION
	 "Type of video installed, e.g., Ultra VGA, Ultra VGA+ etc."
   ::= { hpnsaSiBasicInfo 15 }

   hpnsaSiNumISASlots OBJECT-TYPE
      SYNTAX INTEGER
      ACCESS read-only
      STATUS mandatory
      DESCRIPTION
	 "Number of ISA slots in the system."
   ::= { hpnsaSiBasicInfo 16 }

-- ****************************************************************************
-- HP NSA System Information Security Group
-- ========================================
--
-- hp                                              (1.3.6.1.4.1.11)
--    nm                                           (hp.2)
--       hpnsa                                     (nm.23)
--          hpnsaSystemInfo Group                  (hpnsa.7)
--             hpnsaSiSecurity Group               (hpnsa.7.4)
--                hpnsaSiPowerOnPassword           (hpnsa.7.4.1)
--                hpnsaSiNetServerMode             (hpnsa.7.4.2)
--                hpnsaSiKeyboardLockPassword      (hpnsa.7.4.3)
--                hpnsaSiVideoBlankMode            (hpnsa.7.4.4)
--                hpnsaSiBootDiskPriority          (hpnsa.7.4.5)
--                hpnsaSiWriteToFloppy             (hpnsa.7.4.6)
--                hpnsaSiKbdMouseInactivityTO      (hpnsa.7.4.7)
--
--  The Security group describes how the security features on your HP
--  computer are currently configured.
--
--  Implementation of the security group is mandatory for all agents that
--  support the HP NSA System Information MIB.
--
-- ****************************************************************************

   hpnsaSiPowerOnPassword OBJECT-TYPE
      SYNTAX INTEGER {
	 n-a(0),
	 disabled(1),
	 enabled(2)
      }
      ACCESS read-only
      STATUS mandatory
      DESCRIPTION
	 "The state of the power on password feature."
   ::= { hpnsaSiSecurity 1 }

   hpnsaSiNetServerMode OBJECT-TYPE
      SYNTAX INTEGER {
	 n-a(0),
	 disabled(1),
	 enabled(2)
      }
      ACCESS read-only
      STATUS mandatory
      DESCRIPTION
	 "The state of the network server mode feature."
   ::= { hpnsaSiSecurity 2 }

   hpnsaSiKeyboardLockPassword OBJECT-TYPE
      SYNTAX INTEGER {
	 n-a(0),
	 disabled(1),
	 enabled(2)
      }
      ACCESS read-only
      STATUS mandatory
      DESCRIPTION
	 "The state of the keyboard lock password feature."
   ::= { hpnsaSiSecurity 3 }

   hpnsaSiVideoBlankMode OBJECT-TYPE
      SYNTAX INTEGER {
	 n-a(0),
	 disabled(1),
	 enabled(2)
      }
      ACCESS read-only
      STATUS mandatory
      DESCRIPTION
	 "The state of the blank-screen feature."
   ::= { hpnsaSiSecurity 4 }

   hpnsaSiBootDiskPriority OBJECT-TYPE
      SYNTAX INTEGER {
	 n-a(0),
	 c-then-a(1),
	 a-then-c(2),
	 c-only(3),
	 a-only(4)
      }
      ACCESS read-only
      STATUS mandatory
      DESCRIPTION
	 "Specifies the priority of disks from which the system will boot."
    ::= { hpnsaSiSecurity 5 }

   hpnsaSiWriteToFloppy OBJECT-TYPE
      SYNTAX INTEGER {
	 n-a(0),
	 disabled(1),
	 enabled(2)
      }
      ACCESS read-only
      STATUS mandatory
      DESCRIPTION
	 "Specifies whether one can write to a floppy."
   ::= { hpnsaSiSecurity 6 }

   hpnsaSiKbdMouseInactivityTO OBJECT-TYPE
      SYNTAX INTEGER {
	 n-a(0),
	 disabled(1),
	 enabled(2)
      }
      ACCESS read-only
      STATUS mandatory
      DESCRIPTION
	 "Specifies the state of the keyboard/mouse inactivity timeout feature."
   ::= { hpnsaSiSecurity 7 }

-- ****************************************************************************
-- HP NSA System Information Port Group
-- ====================================
--
-- hp                                              (1.3.6.1.4.1.11)
--    nm                                           (hp.2)
--       hpnsa                                     (nm.23)
--          hpnsaSystemInfo Group                  (hpnsa.7)
--             hpnsaSiPort Group                   (hpnsa.7.5)
--                hpnsaSiPortTable                 (hpnsa.7.5.1)
--                   hpnsaSiPortEntry              (hpnsa.7.5.1.1)
--                      hpnsaSiPortIndex           (hpnsa.7.5.1.1.1)
--                      hpnsaSiPortType            (hpnsa.7.5.1.1.2)
--                      hpnsaSiPortStartAddress    (hpnsa.7.5.1.1.3)
--                      hpnsaSiPortEndAddress      (hpnsa.7.5.1.1.4)
--                      hpnsaSiPortInterruptNum    (hpnsa.7.5.1.1.5)
--
-- The Port group provides information on the system serial and parallel ports
--
-- Implementation of the port group is mandatory for all agents that
-- support the HP NSA System Information MIB.
--
-- ****************************************************************************

   hpnsaSiPortTable OBJECT-TYPE
      SYNTAX SEQUENCE OF HPnsaSiPortEntry
      ACCESS not-accessible
      STATUS mandatory
      DESCRIPTION
	 "A table of port informaton for the system."
   ::= { hpnsaSiPort 1 }

   hpnsaSiPortEntry OBJECT-TYPE
      SYNTAX HPnsaSiPortEntry
      ACCESS not-accessible
      STATUS mandatory
      DESCRIPTION
	 "System port information."
      INDEX { hpnsaSiPortIndex }
   ::= { hpnsaSiPortTable 1 }

   HPnsaSiPortEntry ::= SEQUENCE {
      hpnsaSiPortIndex           INTEGER,
      hpnsaSiPortType            INTEGER,
      hpnsaSiPortStartAddress    INTEGER,
      hpnsaSiPortEndAddress      INTEGER,
      hpnsaSiPortInterruptNum    INTEGER
   }

   hpnsaSiPortIndex OBJECT-TYPE
      SYNTAX INTEGER
      ACCESS read-only
      STATUS mandatory
      DESCRIPTION
	 "A unique port index."
   ::= { hpnsaSiPortEntry 1 }

   hpnsaSiPortType OBJECT-TYPE
      SYNTAX INTEGER {
	 serial(1),
	 parallel(2)
      }
      ACCESS read-only
      STATUS mandatory
      DESCRIPTION
	 "Type of port.  Serial = 1, parallel = 2."
   ::= { hpnsaSiPortEntry 2 }

   hpnsaSiPortStartAddress OBJECT-TYPE
      SYNTAX INTEGER
      ACCESS read-only
      STATUS mandatory
      DESCRIPTION
	 "Port start address."
   ::= { hpnsaSiPortEntry 3 }

   hpnsaSiPortEndAddress OBJECT-TYPE
      SYNTAX INTEGER
      ACCESS read-only
      STATUS mandatory
      DESCRIPTION
	 "Port end address."
   ::= { hpnsaSiPortEntry 4 }

   hpnsaSiPortInterruptNum OBJECT-TYPE
      SYNTAX INTEGER
      ACCESS read-only
      STATUS mandatory
      DESCRIPTION
	 "Interrupt number for this port."
   ::= { hpnsaSiPortEntry 5 }

-- ****************************************************************************
-- HP NSA System Information Memory Table
-- ======================================
--
-- hp                                              (1.3.6.1.4.1.11)
--    nm                                           (hp.2)
--       hpnsa                                     (nm.23)
--          hpnsaSystemInfo Group                  (hpnsa.7)
--             hpnsaSiMemory Group                 (hpnsa.7.6)
--                hpnsaSiBaseMemSize               (hpnsa.7.6.1)
--                hpnsaSiExtMemSize                (hpnsa.7.6.2)
--                hpnsaSiMemType                   (hpnsa.7.6.3)
--                hpnsaSiMemSpeed                  (hpnsa.7.6.4)
--
-- ****************************************************************************

   hpnsaSiBaseMemSize OBJECT-TYPE
      SYNTAX INTEGER (0..2147483647)
      ACCESS read-only
      STATUS mandatory
      DESCRIPTION
	 "Size of base memory installed, in KB."
      ::= { hpnsaSiMemory 1 }

   hpnsaSiExtMemSize OBJECT-TYPE
      SYNTAX INTEGER (0..2147483647)
      ACCESS read-only
      STATUS mandatory
      DESCRIPTION
	 "Size of extended memory installed, in KB."
   ::= { hpnsaSiMemory 2 }

   hpnsaSiMemType OBJECT-TYPE
      SYNTAX INTEGER {
	 other(0),
	 on-board(1),
	 singleWidthModule(2),
	 doubleWidthModule(3),
	 simm(4)
      }
      ACCESS read-only
      STATUS optional
      DESCRIPTION
	 "Type of memory installed.  The value other(0) will be
	  given if the type is not known.  The value board(1) will be
	  given if the memory module is permanently mounted (not modular)
	  on a system board or memory expansion board."
   ::= { hpnsaSiMemory 3 }

   hpnsaSiMemSpeed OBJECT-TYPE
      SYNTAX INTEGER (0..65535)
      ACCESS read-only
      STATUS optional
      DESCRIPTION
	 "Memory speed in nanoseconds.  The value zero (0) will
	  be given if the module speed cannot be determined."
   ::= { hpnsaSiMemory 4 }

-- ****************************************************************************
-- HP NSA System Information Hard Disk Table
-- =========================================
--
-- hp                                              (1.3.6.1.4.1.11)
--    nm                                           (hp.2)
--       hpnsa                                     (nm.23)
--          hpnsaSystemInfo Group                  (hpnsa.7)
--             hpnsaSiHardDisk Group               (hpnsa.7.7)
--                hpnsaSiNumHardDisks              (hpnsa.7.7.1)
--                hpnsaSiHardDiskTable             (hpnsa.7.7.2)
--                   hpnsaSiHardDiskEntry          (hpnsa.7.7.2.1)
--                      hpnsaSiHardDiskIndex       (hpnsa.7.7.2.1.1)
--                      hpnsaSiHardDiskType        (hpnsa.7.7.2.1.2)
--                      hpnsaSiHardDiskCylinders   (hpnsa.7.7.2.1.3)
--                      hpnsaSiHardDiskSectors     (hpnsa.7.7.2.1.4)
--                      hpnsaSiHardDiskHeads       (hpnsa.7.7.2.1.5)
--                      hpnsaSiHardDiskCapacity    (hpnsa.7.7.2.1.6)
--
-- ****************************************************************************

   hpnsaSiNumHardDisks OBJECT-TYPE
      SYNTAX INTEGER
      ACCESS read-only
      STATUS mandatory
      DESCRIPTION
	 "Number of hard disks installed in the system."
   ::= { hpnsaSiHardDisk 1 }

   hpnsaSiHardDiskTable OBJECT-TYPE
      SYNTAX SEQUENCE OF HPnsaSiHardDiskEntry
      ACCESS not-accessible
      STATUS mandatory
      DESCRIPTION
	 "A table of hard disk information."
   ::= { hpnsaSiHardDisk 2 }

   hpnsaSiHardDiskEntry OBJECT-TYPE
      SYNTAX HPnsaSiHardDiskEntry
      ACCESS not-accessible
      STATUS mandatory
      DESCRIPTION
	 "Hard Disk information."
      INDEX { hpnsaSiHardDiskIndex }
   ::= { hpnsaSiHardDiskTable 1 }

   HPnsaSiHardDiskEntry ::= SEQUENCE {
      hpnsaSiHardDiskIndex       INTEGER,
      hpnsaSiHardDiskType        INTEGER,
      hpnsaSiHardDiskCylinders   INTEGER,
      hpnsaSiHardDiskSectors     INTEGER,
      hpnsaSiHardDiskHeads       INTEGER,
      hpnsaSiHardDiskCapacity    INTEGER
   }

   hpnsaSiHardDiskIndex OBJECT-TYPE
      SYNTAX INTEGER
      ACCESS read-only
      STATUS mandatory
      DESCRIPTION
	 "Index of the hard disk."
   ::= { hpnsaSiHardDiskEntry 1 }

   hpnsaSiHardDiskType OBJECT-TYPE
      SYNTAX INTEGER
      ACCESS read-only
      STATUS mandatory
      DESCRIPTION
	 "The configured hard disk type."
   ::= { hpnsaSiHardDiskEntry 2 }

   hpnsaSiHardDiskCylinders OBJECT-TYPE
      SYNTAX INTEGER
      ACCESS read-only
      STATUS mandatory
      DESCRIPTION
	 "Number of cylinders on the hard disk."
   ::= { hpnsaSiHardDiskEntry 3 }

   hpnsaSiHardDiskSectors OBJECT-TYPE
      SYNTAX INTEGER
      ACCESS read-only
      STATUS mandatory
      DESCRIPTION
	 "Number of sectors per track on the hard disk."
   ::= { hpnsaSiHardDiskEntry 4 }

   hpnsaSiHardDiskHeads OBJECT-TYPE
      SYNTAX INTEGER
      ACCESS read-only
      STATUS mandatory
      DESCRIPTION
	 "Number of heads on the hard disk."
   ::= { hpnsaSiHardDiskEntry 5 }

   hpnsaSiHardDiskCapacity OBJECT-TYPE
      SYNTAX INTEGER
      ACCESS read-only
      STATUS mandatory
      DESCRIPTION
	 "Capacity of the hard disk in megabytes."
   ::= { hpnsaSiHardDiskEntry 6 }

-- ****************************************************************************
-- HP NSA System Information Floppy Drive Table
-- ============================================
--
-- hp                                              (1.3.6.1.4.1.11)
--    nm                                           (hp.2)
--       hpnsa                                     (nm.23)
--          hpnsaSystemInfo Group                  (hpnsa.7)
--             hpnsaSiFloppyDrive Group            (hpnsa.7.8)
--                hpnsaSiNumFloppyDrives           (hpnsa.7.8.1)
--                hpnsaSiFloppyDriveTable          (hpnsa.7.8.2)
--                   hpnsaSiFloppyDriveEntry       (hpnsa.7.8.2.1)
--                      hpnsaSiFloppyDriveIndex    (hpnsa.7.8.2.1.1)
--                      hpnsaSiFloppyDriveType     (hpnsa.7.8.2.1.2)
--
-- ****************************************************************************

   hpnsaSiNumFloppyDrives OBJECT-TYPE
      SYNTAX INTEGER
      ACCESS read-only
      STATUS mandatory
      DESCRIPTION
	 "Number of floppy drives installed in the system."
   ::= { hpnsaSiFloppyDrive 1 }

   hpnsaSiFloppyDriveTable OBJECT-TYPE
      SYNTAX SEQUENCE OF HPnsaSiFloppyDriveEntry
      ACCESS not-accessible
      STATUS mandatory
      DESCRIPTION
	 "A table of floppy drive information."
   ::= { hpnsaSiFloppyDrive 2 }

   hpnsaSiFloppyDriveEntry OBJECT-TYPE
      SYNTAX HPnsaSiFloppyDriveEntry
      ACCESS not-accessible
      STATUS mandatory
      DESCRIPTION
	 "Floppy drive information."
      INDEX { hpnsaSiFloppyDriveIndex }
   ::= { hpnsaSiFloppyDriveTable 1 }

   HPnsaSiFloppyDriveEntry ::= SEQUENCE {
      hpnsaSiFloppyDriveIndex     INTEGER,
      hpnsaSiFloppyDriveType      INTEGER
   }

   hpnsaSiFloppyDriveIndex OBJECT-TYPE
      SYNTAX INTEGER
      ACCESS read-only
      STATUS mandatory
      DESCRIPTION
	 "Index of the floppy drive."
   ::= { hpnsaSiFloppyDriveEntry 1 }

   hpnsaSiFloppyDriveType OBJECT-TYPE
      SYNTAX INTEGER {
	 unknown(0),
	 m-360K(1),
	 m-1-2MB(2),
	 m-1-2-MB(3),
	 m-1-44MB(4)
      }
      ACCESS read-only
      STATUS mandatory
      DESCRIPTION
	 "Type of floppy drive."
   ::= { hpnsaSiFloppyDriveEntry 2 }

END
