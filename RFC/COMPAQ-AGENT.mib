-- Revision 1.6
-- Copyright 2000 Compaq Inc.
-- All rights reserved.

COMPAQ-AGENT-MIB  DEFINITIONS ::= BEGIN

    IMPORTS
        IpAddress			FROM RFC1155-SMI
        OBJECT-TYPE         FROM RFC-1212
        DisplayString		FROM RFC1213-MIB
        compaq-common-mgmt  FROM COMPAQ-ID-REC  
        cpqRackAssetIndex,
        cpqRackCommonEnclosureRack,
        cpqRackCommonEnclosureIndex,
        cpqRackNetConnectorRack,
        cpqRackNetConnectorChassis,
        cpqRackNetConnectorIndex
        					FROM CPQRACK
        ;
    	
--      agentGeneralMgmt MODULE-IDENTITY
--	    LAST-UPDATED "0007150000Z"
--	    ORGANIZATION "COMPAQ, Inc."
--	    CONTACT-INFO
--	        "   COMPAQ Customer Service
--
--		    Postal: 
--
--		       Tel: 
--
--		    E-mail: "
--	    DESCRIPTION
--		    "The Structure of Common Management Information for the
--		    Compaq enterprise."
--        ::= {  compaq-common-mgmt 1 }

		agentGeneralMgmt		OBJECT IDENTIFIER ::= { compaq-common-mgmt 1 }
        
		agentBasicInfo          OBJECT IDENTIFIER ::= { agentGeneralMgmt 1 }
		agentBasicConfig        OBJECT IDENTIFIER ::= { agentGeneralMgmt 2 }
		agentIpProtoConfig      OBJECT IDENTIFIER ::= { agentGeneralMgmt 3 }
		agentIpTrapManager		OBJECT IDENTIFIER ::= { agentGeneralMgmt 4 }
		agentConsoleModeManager	OBJECT IDENTIFIER ::= { agentGeneralMgmt 5 }
		agentSlipModeManager	OBJECT IDENTIFIER ::= { agentGeneralMgmt 6 }
		agentSNTP				OBJECT IDENTIFIER ::= { agentGeneralMgmt 7 }
		agentDST			OBJECT IDENTIFIER ::= { agentGeneralMgmt 8 }
		
		agentSwitchCommonMgmt   OBJECT IDENTIFIER ::= { compaq-common-mgmt 3 }
		
		agentSwitchCube			OBJECT IDENTIFIER ::= { agentSwitchCommonMgmt 1 }
		agentSwitchPowerSupply 	OBJECT IDENTIFIER ::= { agentSwitchCommonMgmt 2 }
		agentSwitchFan 			OBJECT IDENTIFIER ::= { agentSwitchCommonMgmt 3 }
		agentSwitchTempSensor 	OBJECT IDENTIFIER ::= { agentSwitchCommonMgmt 4 }
		
		
-- ****************
-- agentBasicInfo *
-- ****************
-- agentBasicInfo          OBJECT IDENTIFIER ::= { agentGeneralMgmt 1 }
        
    agentMgmtProtocolCapability OBJECT-TYPE
        SYNTAX  INTEGER {   
                    other(1),
                    snmp-ip(2),
                    snmp-ipx(3),
                    snmp-ip-ipx(4)
                }
        ACCESS  read-only
        STATUS  mandatory
        DESCRIPTION
            "The network management protocol(s) supported by this agent."
        ::= { agentBasicInfo 1 }


-- *************************
-- agentMibcapabilityTable *
-- *************************

    agentMibCapabilityTable OBJECT-TYPE
        SYNTAX  SEQUENCE OF AgentMibCapabilityEntry
        ACCESS  not-accessible
        STATUS  mandatory
        DESCRIPTION
            "A list of MIB capability entries supported by this agent."    
        ::= { agentBasicInfo 2 }

    agentMibCapabilityEntry OBJECT-TYPE
        SYNTAX  AgentMibCapabilityEntry
        ACCESS  not-accessible
        STATUS  mandatory
        DESCRIPTION
            "A MIB capability entry contains objects describing a particular MIB
             supported by this agent."
        INDEX   { agentMibCapabilityIndex }
        ::= { agentMibCapabilityTable 1 }

    AgentMibCapabilityEntry ::= 
        SEQUENCE {
            agentMibCapabilityIndex
                INTEGER,
            agentMibCapabilityDescr
                DisplayString,
            agentMibCapabilityVersion
                INTEGER,
            agentMibCapabilityType
                INTEGER
        }

    agentMibCapabilityIndex OBJECT-TYPE
        SYNTAX  INTEGER
        ACCESS  read-only
        STATUS  mandatory
        DESCRIPTION
            "A list of agentMibCapabilityDescr entries."
        ::= { agentMibCapabilityEntry 1 }

    agentMibCapabilityDescr OBJECT-TYPE
        SYNTAX  DisplayString (SIZE (0..35))
        ACCESS  read-only
        STATUS  mandatory
        DESCRIPTION
            "The name of the MIB supported by the agent."
        ::= { agentMibCapabilityEntry 2 }

    agentMibCapabilityVersion OBJECT-TYPE
        SYNTAX  INTEGER
        ACCESS  read-only
        STATUS  mandatory
        DESCRIPTION
            "The version of the MIB specified in this entry."
        ::= { agentMibCapabilityEntry 3 }

    agentMibCapabilityType OBJECT-TYPE
        SYNTAX  INTEGER {
                    other(1),
                    standard(2),
                    proprietary(3),
                    experiment(4)
                }
        ACCESS  read-only
        STATUS  mandatory
        DESCRIPTION
            "The type of the MIB specified in this entry."
        ::= { agentMibCapabilityEntry 4 }


    agentStatusConsoleInUse   OBJECT-TYPE
        SYNTAX INTEGER {
               other(1),
               in-use(2),
               not-in-use(3)
               }
        ACCESS read-only
        STATUS mandatory
        DESCRIPTION
            "This indicates whether console is currently in-use."
        ::= { agentBasicInfo 3 }

    agentStatusSaveCfg OBJECT-TYPE
        SYNTAX INTEGER {
               other(1),
               proceeding(2),
               completed(3),
               changed-not-save(4),
               failed(5)
               }
        ACCESS read-only
        STATUS mandatory
        DESCRIPTION
            "This indicates the status of the device configuration.
            
            other(1) - this entry is currently in use but the conditions 
                     under which it will remain so are different from each 
                     of the following values.
            proceeding(2) - the device configuration is being currently saved into the NV-RAM.
            completed(3) – all of the device configuration parameters have been
                     saved into NV-RAM.
            changed-not-save(4)– some of the device configuration parameters have
                     been changed but not saved into NV-RAM.
            failed(5) - The process to save device configuration is failed."
        ::= { agentBasicInfo 4 }
        
	agentSwitchMfgDate OBJECT-TYPE
        SYNTAX  DisplayString (SIZE (0..64))
        ACCESS  read-only
        STATUS  mandatory
        DESCRIPTION
            "The switch manufacturing date and time."
        ::= { agentBasicInfo 5 }
        
	agentSwitchFirmwareMfgDate OBJECT-TYPE
        SYNTAX  DisplayString (SIZE (0..64))
        ACCESS  read-only
        STATUS  mandatory
        DESCRIPTION
            "The switch firmware manufacturing date and time."
        ::= { agentBasicInfo 6 }
        
--     agentSwitchSlotID OBJECT-TYPE
--     	SYNTAX	INTEGER{
--     			other(1),
--     			slotA(2),
--     			slotB(3)	
--     			}
--     	ACCESS read-only
--     	STATUS	mandatory
--     	DESCRIPTION
--     		"The slot ID of the switch"
--     	::= { agentBasicInfo 7 }
     
 --    agentSwitchSafeModeStatus OBJECT-TYPE
 --    	SYNTAX	INTEGER{
 --    			false(1),
 --    			true(2)
 --    			}
 --    	ACCESS read-write
 --    	STATUS	mandatory
 --    	DESCRIPTION
 --    		"The safe mode status of the switch"
 --    	::= { agentBasicInfo 8 }

-- ******************
-- agentBasicConfig *
-- ******************
-- agentBasicConfig        OBJECT IDENTIFIER ::= { agentGeneralMgmt 2 }   

    agentBscSwFileTable OBJECT-TYPE
        SYNTAX  SEQUENCE OF AgentBscSwFileEntry
        ACCESS  not-accessible
        STATUS  mandatory
        DESCRIPTION
            "A list of MIB Basic Config entries supported file Update by this agent."    
        ::= { agentBasicConfig 1 }    
        
    agentBscSwFileEntry OBJECT-TYPE
        SYNTAX  AgentBscSwFileEntry
        ACCESS  not-accessible
        STATUS  mandatory
        DESCRIPTION
            "A basic config entry contains objects describing a particular MIB
             supported by this agent."
        INDEX   { agentBscSwFileIndex }
        ::= { agentBscSwFileTable 1 }        

    AgentBscSwFileEntry ::=
    	SEQUENCE {
    		agentBscSwFileIndex
    			INTEGER,
    		agentBscSwFileDscr
    			DisplayString,
    		agentBscSwFileAddr
    			IpAddress,
    		agentBscSwFileTransferType
    			INTEGER,
        	agentBscSwFile
        		DisplayString,
        	agentBscSwFileLocateId
        		INTEGER,
        	agentBscSwFileLoadType
        		INTEGER,
        	agentBscSwFileCtrl
        		INTEGER,
        	agentBscFileServerTftpPort
        		INTEGER,
        	agentBscSwFileTime
        		DisplayString,
        	agentBscSwFileStatus
        		DisplayString
        }

    agentBscSwFileIndex OBJECT-TYPE
    	SYNTAX	INTEGER
    	ACCESS	read-write
    	STATUS	mandatory
    	DESCRIPTION
    		"The table index for the file entry"
    	::= { agentBscSwFileEntry 1 }

    agentBscSwFileDscr OBJECT-TYPE
        SYNTAX  DisplayString  (SIZE (0..64))
        ACCESS  read-write
        STATUS  mandatory
        DESCRIPTION
            "The description for the purpose of the software file in this entry.
			 Note:
			 For system which does not support change of this object, setting value to 
			 this object will cause the system to return bad-value error message.
			 "
        ::= { agentBscSwFileEntry 2 }
        
    agentBscSwFileAddr OBJECT-TYPE
        SYNTAX  IpAddress
        ACCESS  read-write
        STATUS  mandatory
        DESCRIPTION
            "The IP address where the File to be downloaded is located, or the IP address
            where the file will be uploaded to."
        ::= {  agentBscSwFileEntry 3 }
            	
    agentBscSwFileTransferType OBJECT-TYPE
        SYNTAX  INTEGER {
                    other(1),
                    network-load(2),
                    out-of-band-load(3)
                }
        ACCESS  read-write
        STATUS  mandatory
        DESCRIPTION
            "The channel through which the file will be downloaded or uploaded. 

			 Note:
			 For system which does not support all channels, setting value to the unsupported 
			 channel will cause the system to return bad-value error message.
			 "
        ::= { agentBscSwFileEntry 4 }

    agentBscSwFile OBJECT-TYPE
        SYNTAX  DisplayString  (SIZE (0..128))
        ACCESS  read-write
        STATUS  mandatory
        DESCRIPTION
            "The name of the file to be downloaded from the TFTP server, or to be uploaded
            to."
        ::= { agentBscSwFileEntry 5 }
        
     agentBscSwFileLocateId OBJECT-TYPE
        SYNTAX  INTEGER (1..16)
        ACCESS  read-write
        STATUS  mandatory
        DESCRIPTION
            "This object describes the type of the file.
             runtime-code(1),
             log-file(2),
             cfg-file(3)
             
			 Note:
			 For system which does not support change of this object, setting value to 
			 this object will cause the system to return bad-value error message.
             " 
        ::= { agentBscSwFileEntry 6 }
        
     agentBscSwFileLoadType OBJECT-TYPE
        SYNTAX  INTEGER {
                    other(1),
                    upload(2),
                    download(3)
                }
        ACCESS  read-write
        STATUS  mandatory
        DESCRIPTION
        	"This object provides the user to select download or upload function for the file.

			 Note:
			 For system which does not support change of this object, setting value to 
			 this object will cause the system to return bad-value error message.
			 "
        ::= { agentBscSwFileEntry 7 }
                                               
     agentBscSwFileCtrl OBJECT-TYPE
        SYNTAX  INTEGER {
                    other(1),
                    inactive(2),
                    start(3),
                    delete(4),
                    create-and-go(5)
                }
        ACCESS  read-write
        STATUS  mandatory
        DESCRIPTION
            "This object provides the user to download runtime software. The setting 
 		  	 will take effect when the system is restart. See Note(1) below
 		  
			 Note:
			 For system which does not support change of this object to some value, 
			 setting object to these values cause the system to return 
			 bad-value error message.
			 "
        ::= { agentBscSwFileEntry 8 }
        
	agentBscFileServerTftpPort OBJECT-TYPE
        SYNTAX  INTEGER
        ACCESS  read-write
        STATUS  mandatory
        DESCRIPTION
            "The IP port used by the TFTP server."
        ::= {  agentBscSwFileEntry 9 }
    
    agentBscSwFileTime OBJECT-TYPE
        SYNTAX      DisplayString (SIZE (0..32))
        ACCESS  read-only
        STATUS      mandatory
        DESCRIPTION
            "Configuration/firmware file last saved Date/Time, NULL if unknown.  
             Unknown if time has not been set by SNTP or manual entry when the 
             configuration/firmware file was saved
            "
    ::= { agentBscSwFileEntry 10 }
    
   agentBscSwFileStatus	OBJECT-TYPE
   		SYNTAX	DisplayString (SIZE (0..256))
        ACCESS  read-only
        STATUS      mandatory
        DESCRIPTION
            "Status of last download attempt.  See trap switchFileInvalid. 
             Read-only initialized to NULL"
    ::= { agentBscSwFileEntry 11 }  

	agentFileTransfer OBJECT-TYPE
		SYNTAX INTEGER {
				other(1),
				start(2),
				start-and-reset(3),
				noaction(4)
			}
		ACCESS read-write
		STATUS obsolete
		DESCRIPTION
			"This object will execute the download or upload action. If start(2), it will
			begin to download/upload, but no reset as follow. If start-and-reset(3), then
			the reset will active after download or upload. No action if(4). 

			 Note:
			 Because these funiction will be limited by the system support. Some of the 
			 select item will invalid. When one of the item user select,it will response with 
			 bad-value status."
		::= { agentBasicConfig 2 }
				
    agentSystemReset OBJECT-TYPE
        SYNTAX  INTEGER {
                    other(1),
                    cold-start(2),
                    warm-start(3),
                    no-reset(4)
                }
        ACCESS  read-write
        STATUS  mandatory
        DESCRIPTION
            "This object indicates the agent system reset state. Setting this
             object to no-reset(4) has no effect. Setting this object to
             cold-start(2) or warm-start(3) will reset the agent. The agent 
             always returns no-reset(4) when this object is read."
        ::= { agentBasicConfig 3 }

    agentRs232PortConfig OBJECT-TYPE
        SYNTAX  INTEGER  {
                    other(1),
                    console(2),
                    out-of-band(3),
					notAvail(4)
                }
        ACCESS  read-write
        STATUS  mandatory
        DESCRIPTION
            "This object indicates the RS-232C mode while device restart."
        ::= { agentBasicConfig 4 }

    agentOutOfBandBaudRateConfig OBJECT-TYPE
        SYNTAX  INTEGER {
                    other(1),
                    baudRate-2400 (2),
                    baudRate-9600 (3),
                    baudRate-19200(4),
                    baudRate-38400(5),
                    baudRate-115200(6)
                }
        ACCESS  read-write
        STATUS  obsolete
        DESCRIPTION
            "This object allows user to specify out_of_band baud rate. It will take effect
			 when the system is restart. 
			 
			 Note:
			 Because these funiction will be limited by the system support. Some of the 
			 select item will invalid. When one of the item user select,it will response with 
			 bad-value status.			 
			 "
        ::= { agentBasicConfig 5 }

     agentSaveCfg OBJECT-TYPE
        SYNTAX INTEGER {
        			other(1),
        			idle(2),
        			set(3)
        		}
        ACCESS read-write
        STATUS mandatory
        DESCRIPTION
            "As the object is set to 'set(3)', the current device configuration will be saved
             into to NV-RAM."
        ::= { agentBasicConfig 6 }                
   
-- ***********************
-- agentIpProtocolConfig *
-- ***********************
-- agentIpProtoConfig      OBJECT IDENTIFIER ::= { agentGeneralMgmt 3 }

    agentIpNumOfIf OBJECT-TYPE
        SYNTAX  INTEGER
        ACCESS  read-only
        STATUS  mandatory
        DESCRIPTION
            "The total number of IP interfaces supported by this agent."
        ::= {  agentIpProtoConfig 1 }

    agentIpTftpServerAddr OBJECT-TYPE
        SYNTAX  IpAddress
        ACCESS  read-write
        STATUS  obsolete
        DESCRIPTION
            "The IP Address of TFTP Server."
        ::= {  agentIpProtoConfig 2 }
	
    agentIpGetIpFrom OBJECT-TYPE
        SYNTAX  INTEGER {
                    other(1),
                    disabled(2),
                    bootp(3),
                    dhcp(4)
                }
        ACCESS  read-write
        STATUS  mandatory
        DESCRIPTION
            "This object indicates whether the agent get its system IP address
             from Bootp/DHCP server at start up."
        ::= { agentIpProtoConfig 3 }	

	-- End of agentIpIfTable ---------        

-- ************************
-- agentIptrapMangerTable *
-- ************************
-- agentIpTrapManager	OBJECT IDENTIFIER ::= { agentGeneralMgmt 4 }
	
    agentIpTrapManagerTable OBJECT-TYPE
        SYNTAX  SEQUENCE OF AgentIpTrapManagerEntry
        ACCESS  not-accessible
        STATUS  mandatory
        DESCRIPTION
            "A list of trap managers to which SNMP traps will be sent."
        ::= {  agentIpTrapManager 1 }

    agentIpTrapManagerEntry OBJECT-TYPE
        SYNTAX  AgentIpTrapManagerEntry
        ACCESS  not-accessible
        STATUS  mandatory
        DESCRIPTION
            "Each entry contains the particular trap manager settings."
        INDEX   { agentIpTrapManagerIpAddr }
        ::= { agentIpTrapManagerTable 1 }

    AgentIpTrapManagerEntry ::= 
        SEQUENCE {
                    agentIpTrapManagerIpAddr
                        IpAddress,
                    agentIpTrapManagerComm
                        DisplayString,
                    agentIpTrapManagerStatus
                        INTEGER
        }

    agentIpTrapManagerIpAddr OBJECT-TYPE
        SYNTAX  IpAddress
        ACCESS  read-only
        STATUS  mandatory
        DESCRIPTION
            "The IP address where SNMP traps will be destined for"
        ::= { agentIpTrapManagerEntry 1 }

    agentIpTrapManagerComm OBJECT-TYPE
        SYNTAX  DisplayString (SIZE (0..20))
        ACCESS  read-write
        STATUS  mandatory
        DESCRIPTION
            "The community string used to encode SNMP trap packet to be sent to the trap
             manager."
        ::= { agentIpTrapManagerEntry 2 }

    agentIpTrapManagerStatus OBJECT-TYPE
        SYNTAX  INTEGER {
                    other(1),
                    disabled(2),
                    enabled(3)
                }
        ACCESS  read-write
        STATUS  mandatory
        DESCRIPTION
            "This object indicates whether or not the trap should be sent to
             this trap manager."
        ::= { agentIpTrapManagerEntry 3 }

-- *****************************************************
-- Add for Slip_Console mode swtich 11-9-2001 WindChen *
-- *****************************************************
-- agentConsoleModeManager	OBJECT IDENTIFIER ::= { agentGeneralMgmt 5 }
	
    agentConsoleModeManagerDataBits OBJECT-TYPE
        SYNTAX  INTEGER {
        		other(1),
        		bits-7(2),
        		bits-8(3)
        	}        
        ACCESS  read-write     
        STATUS  mandatory
        DESCRIPTION
            "The DataBits for console mode, If the agentRs232PortConfig change to console mode
            then the device will use this group to make a setup for console value and 
            agentSlipModeManager group will deactive automatically. "
        ::= { agentConsoleModeManager 1 }

    agentConsoleModeManagerStopBits OBJECT-TYPE
        SYNTAX  INTEGER {
        		other(1),
        		stopbits-1(2),
        		stopbits-2(3)
        	}        
        ACCESS  read-write     
        STATUS  mandatory
        DESCRIPTION
            "The Stop Bits for console mode "
        ::= { agentConsoleModeManager 2 }

    agentConsoleModeManagerParity OBJECT-TYPE
        SYNTAX  INTEGER {
        		none(1),
        		odd(2),
        		even(3)
        	}        
        ACCESS  read-write     
        STATUS  mandatory
        DESCRIPTION
            "The Parity for console mode, If the agentRs232PortConfig change to console mode
            then the device will use this group to make a setup for console value and  
            agentSlipModeManager group will deactive automatically. "
        ::= { agentConsoleModeManager 3 }
        
    agentConsoleModeManagerBaudRate OBJECT-TYPE
        SYNTAX  INTEGER {
                    other(1),
                    baudRate-2400(2),
                    baudRate-9600(3),
                    baudRate-19200(4),
                    baudRate-38400(5),
                    baudRate-57200(6),
                    baudRate-115200(7)
                    
                }
        ACCESS  read-write
        STATUS  mandatory
        DESCRIPTION
            "The transmit rate for console mode."
        ::= { agentConsoleModeManager 4 }
        
-- *******************
-- Slip Mode Manager *
-- *******************	
-- agentSlipModeManager	OBJECT IDENTIFIER ::= { agentGeneralMgmt 6 }

    agentSlipModeManagerLocalIP OBJECT-TYPE
        SYNTAX  IpAddress
        ACCESS  read-write
        STATUS  mandatory
        DESCRIPTION
            "The Local IP address for slip mode, If the agentRs232PortConfig change to out-of-band mode
            then the device will use this group to make a setup for slip value and  agentConsoleModeManager
            group will deactive automatically. "
        ::= { agentSlipModeManager 1 }
	
    agentSlipModeManagerRemoteIP OBJECT-TYPE
        SYNTAX  IpAddress
        ACCESS  read-write
        STATUS  mandatory
        DESCRIPTION
            "The Remote IP address for slip mode "
        ::= { agentSlipModeManager 2 }
        
    agentSlipModeManagerMTU OBJECT-TYPE
        SYNTAX  INTEGER {
                    other(1),
                    mtu-1006(2),
                    mtu-1500(3)
                }
        ACCESS  read-write
        STATUS  mandatory
        DESCRIPTION
            "The MTU Value for Slip Mode "
        ::= { agentSlipModeManager 3 }
        
    agentSlipModeManagerBaudRate OBJECT-TYPE
        SYNTAX  INTEGER {
                    other(1),
                    baudRate-2400(2),
                    baudRate-9600(3),
                    baudRate-19200(4),
                    baudRate-38400(5),
                    baudRate-57200(6),
                    baudRate-115200(7)
                    
                }
        ACCESS  read-write
        STATUS  mandatory
        DESCRIPTION
            "The MTU Value for Slip Mode "
        ::= { agentSlipModeManager 4 }

-- ************************
-- agentSNTP              *
-- ************************
    
-- agentSNTP	OBJECT IDENTIFIER ::= { agentGeneralMgmt 7 }
    
	agentSNTPState OBJECT-TYPE
    	SYNTAX	INTEGER {
                	other(1),
                	disabled(2),
                	enabled(3)
                }
        ACCESS  read-write
        STATUS  mandatory
        DESCRIPTION
        	"This object enable/disable the SNTP function."
        ::= { agentSNTP 1 }
         
    agentSNTPTimeSource OBJECT-TYPE
        SYNTAX  INTEGER{
        			system(0),
                	server1(1),
                	server2(2)
                }
        ACCESS  read-only
        STATUS  mandatory
        DESCRIPTION
            "the SNTP server status for time source changing"
        ::= { agentSNTP 2 }
         
    agentSNTPServer1IPAddr OBJECT-TYPE
        SYNTAX  IpAddress
        ACCESS  read-write
        STATUS  mandatory
        DESCRIPTION
            "Configure the SNTP server #1 IP address"
        ::= { agentSNTP 3 }
        
    agentSNTPServer2IPAddr OBJECT-TYPE
        SYNTAX  IpAddress
        ACCESS  read-write
        STATUS  mandatory
        DESCRIPTION
            "Configure the SNTP server #2 IP address"
        ::= { agentSNTP 4 }

    agentSNTPTimeZone OBJECT-TYPE
        SYNTAX  INTEGER (-779..839)
        ACCESS  read-write
        STATUS  mandatory
        DESCRIPTION
            "Local time offset in minutes from GMT."
        ::= { agentSNTP 5 }

    agentSNTPPollInterval OBJECT-TYPE
        SYNTAX  INTEGER (30..99999)
        ACCESS  read-write
        STATUS  mandatory
        DESCRIPTION
            "Update time in seconds from SNTP server."
--	    DEFVAL  { 1024 }
        ::= { agentSNTP 6 }
        
	agentSNTPCurrentTime	OBJECT-TYPE
		SYNTAX	DisplayString (SIZE (0..32))
		ACCESS read-only
		STATUS	mandatory
		DESCRIPTION
			"the mandatory network time was got from the SNTP server"
		::= { agentSNTP 7 }
		
	agentSNTPUpTime			OBJECT-TYPE
		SYNTAX	INTEGER
		ACCESS read-only
		STATUS mandatory
		DESCRIPTION
			"The time (in second) since the network management portion 
			of the system was last re-initialized. It is the same as 
			sysUptime."
		::= { agentSNTP 8 }
	
	agentSNTPBootTime		OBJECT-TYPE
		SYNTAX	DisplayString (SIZE (0..32))
		ACCESS read-only
		STATUS mandatory
		DESCRIPTION
			"The boot time of the switch is equal to subtract systemUpTime
			from agentSNTPNetworkTime"
		::= { agentSNTP 9 }
        
-- ***********
-- agentDST  *
-- ***********
    
-- agentDST	OBJECT IDENTIFIER ::= { agentGeneralMgmt 8 }

	agentDSTStatus 	OBJECT-TYPE
        SYNTAX	INTEGER{
        			disable(1),
     				repeating(2),
     				annual(3)
     			}
        ACCESS    read-write
        STATUS        mandatory
        DESCRIPTION
            "An indication of whether the DST(Daylight Saving Time) feature 
             is enabled on this device. When this object is set to repeating(2),
             or annual(3) then all the other objects are set to default values. 
             When this object is set to disable(1), then all the other objects 
             are not instantiated and the DST feature is disabled"
        ::= { agentDST 1 }

    agentDSTOffset	OBJECT-TYPE
        SYNTAX        INTEGER ( 0 .. 1440) 
        ACCESS    read-write
        STATUS        mandatory
        DESCRIPTION   
            "The value of this object indicates number of minutes to add 
             or to subtract during DST. This object is not instantiated
             when agentDSTStatus object is set to false."                       
        ::= { agentDST 2 }

   	agentDSTRepeatingStartMonth		OBJECT-TYPE
		SYNTAX	INTEGER (1 .. 12)
        ACCESS    read-write
        STATUS        mandatory
        DESCRIPTION
        	"the repeating start month (January = 1, .., Decenber = 12)"
        ::= { agentDST 3 }   
   
   	agentDSTRepeatingStartWhichDay	OBJECT-TYPE
   		SYNTAX	INTEGER (0 .. 4)
        ACCESS    read-write
        STATUS        mandatory
        DESCRIPTION
        	"WhichDay means  
        		0 = last week 
        		1 = 1st week
        		2 = 2nd week
        		3 = 3th week
        		4 = 4th week
        	"
        ::= { agentDST 4 } 
   
   	agentDSTRepeatingStartDayOfWeek	OBJECT-TYPE
   		SYNTAX	INTEGER (1 .. 7 )
        ACCESS    read-write
        STATUS        mandatory
        DESCRIPTION
        	"Day Of Week
        		Sun = 1
        		Mon = 2
        		Tue = 3
        		Wed = 4
        		Thu = 5
        		Fri = 6
        	    Sat = 7 
        	"
        ::= { agentDST 5 } 
   
   	agentDSTRepeatingStartHour		OBJECT-TYPE
   		SYNTAX	INTEGER (0 .. 23)
        ACCESS    read-write
        STATUS        mandatory
        DESCRIPTION
        	"the hour of the DST Repeating Start Day of Week"
        ::= { agentDST 6 } 
   
   	agentDSTRepeatingStartMinute	OBJECT-TYPE
   		SYNTAX	INTEGER (0 .. 59)
        ACCESS    read-write
        STATUS        mandatory
        DESCRIPTION
        	"the minute of the DST Repeating Start Hour"
        ::= { agentDST 7 } 
   
   	agentDSTRepeatingEndMonth		OBJECT-TYPE
   		SYNTAX	INTEGER (1 .. 12)
        ACCESS    read-write
        STATUS        mandatory
        DESCRIPTION
        	"the repeating end month (January = 1, .., Decenber = 12)"
        ::= { agentDST 8 } 
   
   	agentDSTRepeatingEndWhichDay	OBJECT-TYPE
   		SYNTAX	INTEGER (0 .. 4)
        ACCESS    read-write
        STATUS        mandatory
        DESCRIPTION
        	"WhichDay means  
        		0 = last week 
        		1 = 1st week
        		2 = 2nd week
        		3 = 3th week
        		4 = 4th week
        	"
        ::= { agentDST 9 } 
   
   	agentDSTRepeatingEndDayOfWeek	OBJECT-TYPE
   		SYNTAX	INTEGER (1 .. 7)
        ACCESS    read-write
        STATUS        mandatory
        DESCRIPTION
        	"Day Of Week
        		Sun = 1
        		Mon = 2
        		Tue = 3
        		Wed = 4
        		Thu = 5
        		Fri = 6
        	    Sat = 7 
        	"
        ::= { agentDST 10 } 
   
   	agentDSTRepeatingEndHour	OBJECT-TYPE
   		SYNTAX	INTEGER (0 .. 23)
        ACCESS    read-write
        STATUS        mandatory
        DESCRIPTION
        	"the hour of the DST Repeating End Day of Week"
        ::= { agentDST 11 } 
   
   	agentDSTRepeatingEndMinute	OBJECT-TYPE
   		SYNTAX	INTEGER (0 .. 59)
        ACCESS    read-write
        STATUS        mandatory
        DESCRIPTION
        	"the minute of the DST Repeating End Hour"
        ::= { agentDST 12 } 
   
   	agentDSTAnnualStartMonth	OBJECT-TYPE
   		SYNTAX	INTEGER (1 .. 12)
        ACCESS    read-write
        STATUS        mandatory
        DESCRIPTION
        	"the annual start month (January = 1, .., Decenber = 12)"
        ::= { agentDST 13 } 
   
   	agentDSTAnnualStartDayOfMonth	OBJECT-TYPE
   		SYNTAX	INTEGER (1 .. 31)
        ACCESS    read-write
        STATUS        mandatory
        DESCRIPTION
        	"the day of annual start month"
        ::= { agentDST 14 } 
   
   	agentDSTAnnualStartHour		OBJECT-TYPE
   		SYNTAX	INTEGER (0 .. 23)
        ACCESS    read-write
        STATUS        mandatory
        DESCRIPTION
        	"the hour of the annual start day"
        ::= { agentDST 15 } 
   
   	agentDSTAnnualStartMinute	OBJECT-TYPE
   		SYNTAX	INTEGER (0 .. 59)
        ACCESS    read-write
        STATUS        mandatory
        DESCRIPTION
        	"the minute of the annual start hour"
        ::= { agentDST 16 } 
   
   	agentDSTAnnualEndMonth		OBJECT-TYPE
   		SYNTAX	INTEGER (1 .. 12)
        ACCESS    read-write
        STATUS        mandatory
        DESCRIPTION
        	"the annual end month (January = 1, .., Decenber = 12)"
        ::= { agentDST 17 } 
   
   	agentDSTAnnualEndDayOfMonth	OBJECT-TYPE
   		SYNTAX	INTEGER (1 .. 31)
        ACCESS    read-write
        STATUS        mandatory
        DESCRIPTION
        	"the day of annual end month"
        ::= { agentDST 18 } 
   
   	agentDSTAnnualEndHour		OBJECT-TYPE
   		SYNTAX	INTEGER (0 .. 23)
        ACCESS    read-write
        STATUS        mandatory
        DESCRIPTION
        	"the hour of annual end day of month"
        ::= { agentDST 19 } 
   
   	agentDSTAnnualEndMinute		OBJECT-TYPE
   		SYNTAX	INTEGER (0 .. 59)
        ACCESS    read-write
        STATUS        mandatory
        DESCRIPTION
        	"the minute of annual end hour"
        ::= { agentDST 20 } 
        
-- ***********************
-- agentSwitchCubeTable  *
-- ***********************
-- agentSwitchCube	OBJECT IDENTIFIER ::= { agentSwitchCommonMgmt 1 } 

	agentSwitchCubeTable OBJECT-TYPE
        SYNTAX  SEQUENCE OF AgentSwitchCubeEntry
        ACCESS  not-accessible
        STATUS  mandatory
        DESCRIPTION
            "A table of cube information."
        ::= { agentSwitchCube 1 }

    agentSwitchCubeEntry OBJECT-TYPE
        SYNTAX  AgentSwitchCubeEntry
        ACCESS  not-accessible
        STATUS  mandatory
        DESCRIPTION
            "A switch cube description."
        INDEX   { cpqRackAssetIndex,
        		  cpqRackCommonEnclosureRack,
        		  cpqRackCommonEnclosureIndex,
        		  cpqRackNetConnectorRack,
        		  cpqRackNetConnectorChassis,
        		  cpqRackNetConnectorIndex,
				  agentSwitchCubeType }
        ::= { agentSwitchCubeTable 1 }

    AgentSwitchCubeEntry ::= SEQUENCE {
    	agentSwitchCubeType							INTEGER,
    	agentSwitchCubeSpareName					DisplayString,
    	agentSwitchCubeSparePartNumber				DisplayString
	}
        
 	agentSwitchCubeType OBJECT-TYPE		
        SYNTAX  INTEGER {
            other(1),
            dualTSX(2),
            quadT(3)	
            }
        ACCESS  read-only
        STATUS  mandatory
        DESCRIPTION
            "This specifies the type of this instance of cube.

            This value will be one of the following:

            other(1)
              Cube type could not be determined.
            
            dualTSX(2)	
              Switch Dual Base-T plus Dual LC Fiber Interconnect Module.
              
            quadT(3)	
              Switch Quad Base-T Copper Interconnect Module.
            "
        ::= { agentSwitchCubeEntry 1 }	
        
     agentSwitchCubeSpareName OBJECT-TYPE
        SYNTAX  DisplayString (SIZE (0..64))
        ACCESS  read-only
        STATUS  mandatory
        DESCRIPTION
            "The name of the cube.

            The string will be empty if the cube does not report the
            name or it could not be determined."
        ::= { agentSwitchCubeEntry 2 }		 
        
     agentSwitchCubeSparePartNumber OBJECT-TYPE
        SYNTAX  DisplayString (SIZE (0..64))
        ACCESS  read-only
        STATUS  mandatory
        DESCRIPTION
            "The spare part number of the cube.

            The string will be empty if the enclosure does not report this
            function."
        ::= { agentSwitchCubeEntry 3 }  
        
-- *****************************
-- agentSwitchPowerSupplyTable *
-- *****************************    
--	agentSwitchPowerSupply OBJECT IDENTIFIER ::= { agentSwitchCommonMgmt 2 }
	
	agentSwitchPowerSupplyTable OBJECT-TYPE
        SYNTAX  SEQUENCE OF AgentSwitchPowerSupplyEntry
        ACCESS  not-accessible
        STATUS  mandatory
        DESCRIPTION
            "A table of power supply information."
        ::= { agentSwitchPowerSupply 1 }

    agentSwitchPowerSupplyEntry OBJECT-TYPE
        SYNTAX  AgentSwitchPowerSupplyEntry
        ACCESS  not-accessible
        STATUS  mandatory
        DESCRIPTION
        	"A switch power supply description."
        INDEX   { cpqRackAssetIndex,
        		  cpqRackCommonEnclosureRack,
        		  cpqRackCommonEnclosureIndex,
        		  cpqRackNetConnectorRack,
        		  cpqRackNetConnectorChassis,
        		  cpqRackNetConnectorIndex,
                  agentSwitchPowerSupplyIndex }
        ::= { agentSwitchPowerSupplyTable 1 }

    AgentSwitchPowerSupplyEntry ::= SEQUENCE {
		agentSwitchPowerSupplyIndex					INTEGER,
		agentSwitchPowerSupplyMaxPwrOutput       	INTEGER,
        agentSwitchPowerSupplyCurPwrOutput       	INTEGER,
        agentSwitchPowerSupplyIntakeTemp			INTEGER,
 		agentSwitchPowerSupplyExhaustTemp			INTEGER,
        agentSwitchPowerSupplyStatus             	INTEGER,
        agentSwitchPowerSupplyInputLineStatus    	INTEGER,
        agentSwitchPowerSupplyCondition          	INTEGER
        }
          
    agentSwitchPowerSupplyIndex OBJECT-TYPE			-- cpqRackPowerSupplyIndex OBJECT-TYPE
        SYNTAX  INTEGER
        ACCESS  read-only
        STATUS  mandatory
        DESCRIPTION
            "A number that uniquely specifies this power supply in the enclosure."
        ::= { agentSwitchPowerSupplyEntry 1 }		-- { cpqRackPowerSupplyEntry 3 }

    agentSwitchPowerSupplyMaxPwrOutput OBJECT-TYPE 	-- cpqRackPowerSupplyMaxPwrOutput OBJECT-TYPE
        SYNTAX  INTEGER
        ACCESS  read-only
        STATUS  mandatory
        DESCRIPTION
            "The maximum power output of the power supply in watts.

            The value will be -1 if the power supply does not report the
            value."
        ::= { agentSwitchPowerSupplyEntry 2 }		-- { cpqRackPowerSupplyEntry 9 }

    agentSwitchPowerSupplyCurPwrOutput OBJECT-TYPE 	-- cpqRackPowerSupplyCurPwrOutput OBJECT-TYPE
        SYNTAX  INTEGER
        ACCESS  read-only
        STATUS  mandatory
        DESCRIPTION
            "The current power output of the power supply in watts.

            The value will be -1 if the power supply does not report the
            value."
        ::= { agentSwitchPowerSupplyEntry 3 }		-- { cpqRackPowerSupplyEntry 10 }

    agentSwitchPowerSupplyIntakeTemp OBJECT-TYPE 	-- cpqRackPowerSupplyIntakeTemp OBJECT-TYPE
        SYNTAX  INTEGER
        ACCESS  read-only
        STATUS  mandatory
        DESCRIPTION
            "The current air temperature at the intake of the power supply
            in degrees celsius.

            The value will be -1 if the power supply does not report the
            value."
        ::= { agentSwitchPowerSupplyEntry 4 } 		-- { cpqRackPowerSupplyEntry 12 }

    agentSwitchPowerSupplyExhaustTemp OBJECT-TYPE 	-- cpqRackPowerSupplyExhaustTemp OBJECT-TYPE
        SYNTAX  INTEGER
        ACCESS  read-only
        STATUS  mandatory
        DESCRIPTION
            "The current air temperature at the exhaust of the power supply
            in degrees celsius.

            The value will be -1 if the power supply does not report the
            value."
        ::= { agentSwitchPowerSupplyEntry 5 } 		-- { cpqRackPowerSupplyEntry 13 }

    agentSwitchPowerSupplyStatus OBJECT-TYPE 		-- cpqRackPowerSupplyStatus OBJECT-TYPE
        SYNTAX  INTEGER {
            noError(1),
            generalFailure(2),
            bistFailure(3),
            fanFailure(4),
            tempFailure(5),
            interlockOpen(6),
            epromFailed(7),
            vrefFailed(8),
            dacFailed(9),
            ramTestFailed(10),
            voltageChannelFailed(11),
            orringdiodeFailed(12),
            brownOut(13),
            giveupOnStartup(14),
            nvramInvalid(15),
            calibrationTableInvalid(16)
            }
        ACCESS  read-only
        STATUS  mandatory
        DESCRIPTION
            "The status of the power supply."
        ::= { agentSwitchPowerSupplyEntry 6 } 		-- { cpqRackPowerSupplyEntry 14 }

    agentSwitchPowerSupplyInputLineStatus OBJECT-TYPE -- cpqRackPowerSupplyInputLineStatus OBJECT-TYPE
        SYNTAX  INTEGER {
            noError(1),
            lineOverVoltage(2),
            lineUnderVoltage(3),
            lineHit(4),
            brownOut(5),
            linePowerLoss(6)
            }
        ACCESS  read-only
        STATUS  mandatory
        DESCRIPTION
            "The status of line input power."
        ::= { agentSwitchPowerSupplyEntry 7 }		-- { cpqRackPowerSupplyEntry 15 }
        
    agentSwitchPowerSupplyCondition OBJECT-TYPE 		-- cpqRackPowerSupplyCondition OBJECT-TYPE
        SYNTAX  INTEGER {
            other(1),
            ok(2),
            degraded(3),
            failed(4)
            }
        ACCESS  read-only
        STATUS  mandatory
        DESCRIPTION
            "The condition of the power supply.

            This value will be one of the following:

            other(1)
              The status could not be determined or not present.

            ok(2)
              The power supply is operating normally.

            degraded(3)
              A temperature sensor, fan or other power supply component is
              outside of normal operating range.

            failed(4)
              A power supply component detects a condition that could
              possibly damage the system."
        ::= { agentSwitchPowerSupplyEntry 8 }		-- { cpqRackPowerSupplyEntry 17 }
        

-- *********************
-- agentSwitchFanTable *
-- *********************
--  agentSwitchFan 			OBJECT IDENTIFIER ::= { agentSwitchCommonMgmt 3 }

	agentSwitchFanTable OBJECT-TYPE
        SYNTAX  SEQUENCE OF AgentSwitchFanEntry
        ACCESS  not-accessible
        STATUS  mandatory
        DESCRIPTION
            "A table of fan information."
        ::= { agentSwitchFan 1 }

    agentSwitchFanEntry OBJECT-TYPE
        SYNTAX  AgentSwitchFanEntry
        ACCESS  not-accessible
        STATUS  mandatory
        DESCRIPTION
            "A switch fan description."
        INDEX   { cpqRackAssetIndex,
        		  cpqRackCommonEnclosureRack,
        		  cpqRackCommonEnclosureIndex,
        		  cpqRackNetConnectorRack,
        		  cpqRackNetConnectorChassis,
        		  cpqRackNetConnectorIndex,
                  agentSwitchFanIndex }
        ::= { agentSwitchFanTable 1 }

    AgentSwitchFanEntry ::= SEQUENCE {
        agentSwitchFanIndex							INTEGER,
        agentSwitchFanCondition              		INTEGER
	}

    agentSwitchFanIndex OBJECT-TYPE 			-- cpqRackCommonEnclosureFanIndex OBJECT-TYPE
        SYNTAX  INTEGER
        ACCESS  read-only
        STATUS  mandatory
        DESCRIPTION
            "A number that uniquely specifies this fan within this server
            enclosure in the rack."
        ::= { agentSwitchFanEntry 1 }		-- { cpqRackCommonEnclosureFanEntry 3 }                        

    agentSwitchFanCondition OBJECT-TYPE		-- cpqRackCommonEnclosureFanCondition OBJECT-TYPE
        SYNTAX  INTEGER {
            other(1),
            ok(2),
            degraded(3),
            failed(4)
            }
        ACCESS  read-only
        STATUS  mandatory
        DESCRIPTION
            "The condition of the fan.

            This value will be one of the following:

            other(1)
              Fan status detection is not supported.

            ok(2)
              The fan is operating properly.

            degraded(3)
              A redundant fan is not operating properly.

            failed(4)
              A non-redundant fan is not operating properly."
        ::= { agentSwitchFanEntry 2 }		-- { cpqRackCommonEnclosureFanEntry 11 }                

-- **********************
-- agentSwitchTempTable *
-- **********************
--  agentSwitchTempSensor 	OBJECT IDENTIFIER ::= { agentSwitchCommonMgmt 4 } 
	
	agentSwitchTempSensorTable OBJECT-TYPE
        SYNTAX  SEQUENCE OF AgentSwitchTempSensorEntry
        ACCESS  not-accessible
        STATUS  mandatory
        DESCRIPTION
            "A table of temperature sensor information."
        ::= { agentSwitchTempSensor 1 }

    agentSwitchTempSensorEntry OBJECT-TYPE
        SYNTAX  AgentSwitchTempSensorEntry
        ACCESS  not-accessible
        STATUS  mandatory
        DESCRIPTION
            "A switch temperature sensor description."
        INDEX   { cpqRackAssetIndex,
        		  cpqRackCommonEnclosureRack,
        		  cpqRackCommonEnclosureIndex,
        		  cpqRackNetConnectorRack,
        		  cpqRackNetConnectorChassis,
        		  cpqRackNetConnectorIndex,
                  agentSwitchTempSensorIndex }
        ::= { agentSwitchTempSensorTable 1 }

    AgentSwitchTempSensorEntry ::= SEQUENCE {
		agentSwitchTempSensorIndex						INTEGER,
		agentSwitchTempSensorCurrent         			INTEGER,
        agentSwitchTempSensorThreshold       			INTEGER,
        agentSwitchTempSensorCondition       			INTEGER,
        agentSwitchTempSensorTempType        			INTEGER
	}

   agentSwitchTempSensorIndex OBJECT-TYPE		-- cpqRackCommonEnclosureTempSensorIndex OBJECT-TYPE
        SYNTAX  INTEGER
        ACCESS  read-only
        STATUS  mandatory
        DESCRIPTION
            "A number that uniquely specifies this temperature sensor within
            this server enclosure in the rack."
        ::= { agentSwitchTempSensorEntry 1 }		-- { cpqRackCommonEnclosureTempEntry 3 }
                        
   agentSwitchTempSensorCurrent OBJECT-TYPE		-- cpqRackCommonEnclosureTempCurrent OBJECT-TYPE
        SYNTAX  INTEGER
        ACCESS  read-only
        STATUS  mandatory
        DESCRIPTION
            "This is the current temperature sensor reading in degrees
            celsius.

            If this value cannot be determined by software, then a value
            of -1 will be returned."
        ::= { agentSwitchTempSensorEntry 2 }		-- { cpqRackCommonEnclosureTempEntry 6 }

    agentSwitchTempSensorThreshold OBJECT-TYPE	-- cpqRackCommonEnclosureTempThreshold OBJECT-TYPE
        SYNTAX  INTEGER
        ACCESS  read-only
        STATUS  mandatory
        DESCRIPTION
            "This is the threshold temperature sensor setting
            in degrees celsius.  This is the temperature in which the
            sensor will be considered to be in a tripped state this
            causing some action to occur depending on the type of
            the sensor.  The action of temperature sensor threshold
            will be indicated by the cpqRackCommonEnclosureTempType
            item.  If the type is blowout(5), then the temperature sensor
            will cause the fans to speed up.  If the type is caution(9),
            then the temperature sensor is in a degraded state.  If the
            type is critical(15), then the server will be considered
            as in a failed state.

            If this value cannot be determined by software, then a value
            of -1 will be returned."
        ::= { agentSwitchTempSensorEntry 3 }		-- { cpqRackCommonEnclosureTempEntry 7 }

    agentSwitchTempSensorCondition OBJECT-TYPE	-- cpqRackCommonEnclosureTempCondition OBJECT-TYPE
        SYNTAX  INTEGER {
            other(1),
            ok(2),
            degraded(3),
            failed(4)
            }
        ACCESS  read-only
        STATUS  mandatory
        DESCRIPTION
            "The Temperature sensor condition.

            This value will be one of the following:

            other(1)
              Temperature could not be determined.

            ok(2)
              The temperature sensor is within the normal operating range.

            degraded(3)
              The temperature sensor is outside of the normal operating range.

            failed(4)
              The temperature sensor detects a condition that could
              possibly damage the system.

            The system will automatically shutdown if the failed(4) condition
            results, so it is unlikely that this value will ever be returned
            by the agent."
        ::= { agentSwitchTempSensorEntry 4 }		-- { cpqRackCommonEnclosureTempEntry 8 }

    agentSwitchTempSensorTempType OBJECT-TYPE		-- cpqRackCommonEnclosureTempType OBJECT-TYPE
        SYNTAX  INTEGER {
            other(1),
            blowout(5),
            caution(9),
            critical(15)
            }
        ACCESS  read-only
        STATUS  mandatory
        DESCRIPTION
            "This specifies the type of this instance of temperature
            sensor.

            This value will be one of the following:

            other(1)
              Temperature threshold type could not be determined.

            blowout(5)
              If a blowout(5) temperature sensor reaches its threshold,
              the fan or fans in the area of the temperature sensor will
              increase in speed in an attempt to reduce the temperature
              before a caution or critical threshold is reached.

            caution(9)
              If a caution(9) temperature sensor reaches its threshold, the
              cpqRackCommonEnclosureTempCondition will be set to degraded(3)
              and the system will either continue or shutdown depending
              on the user preferences.

            critical(15)
              If a critical(15) temperature sensor reaches its threshold,
              the cpqHeTemperatureCondition will be set to failed(4)
              and the system will shutdown."
        ::= { agentSwitchTempSensorEntry 5 }		-- { cpqRackCommonEnclosureTempEntry 9 } 
        
	endOfMIB    OBJECT-TYPE
        SYNTAX  INTEGER
        ACCESS  read-only
        STATUS  mandatory
        DESCRIPTION
            "End of MIB"
        ::= { agentSwitchCommonMgmt 9999 }

END
