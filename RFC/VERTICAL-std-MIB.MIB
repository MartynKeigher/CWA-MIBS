VERTICAL-std-MIB DEFINITIONS ::= BEGIN

IMPORTS
             Gauge, enterprises
                     FROM RFC1155-SMI
             DisplayString
                     FROM RFC1213-MIB
             OBJECT-TYPE
                     FROM RFC-1212
             TRAP-TYPE
                     FROM RFC-1215;
             

vertical OBJECT IDENTIFIER ::= { enterprises 2338 }  


     --  This MIB module uses the extended OBJECT-TYPE macro as
     --  defined in RFC 1212.
  
     --  This is the MIB module for Vertical Networks' Self 
	 --  Test Daemon, which is responsible for starting and
	 --  monitoring each InstantOffice component (executable,
	 --  service and drivers).
	 --  This MIB is found in the private.enterprise branch 
	 --  of the MIB tree.

     --  Author  : Raju Viswambharan
     --  Version : 1.0
     --  Date    : 18 June, 1998
     --  Comments : created
 

     -- This MIB is structured into two groups:
	
     --	The System Group: Which contains status information
	 --                about the InstantOffice system itself
     --	The Component Group: Contains status information    
	 --               about all components (executables, 
	 --               services and drivers) witihin the system
	 
	 selfTestDaemon    OBJECT IDENTIFIER ::= {vertical 8}
								   
    
     -- The system Group

     -- Implementation of this group is mandatory for all 
	 -- Vertical InstantOffice systems.  
--Bug Fixes : #6472, #10030
	 stdSystemGroup
       OBJECT IDENTIFIER ::= { selfTestDaemon 1 }

        -- madhu 02 09 2001 #4743;  running(1) value changed as "0"
       sysOperStatus OBJECT-TYPE
             SYNTAX  INTEGER {
						running				(0),
						startUpInProgress	(2),
						upgradeInProgress	(3),
						restoreInProgress	(4),
						error               (5)
					}    
             ACCESS  read-only
             STATUS  mandatory
             DESCRIPTION
                "Specifies the current operational status of 
				 the InstantOffice system. Valid values are:
				 running		   (1) -> The normal 
				                          operational status,
										  all components are
										  up and running.
				 startUpInProgress (2) -> The ST Deamon is 
				                          starting up the 
										  system.
				 upgradeInProgress (3) -> The ST Daemon is 
										  attempting to 
										  upgrade the system.
				 restoreInProgress (4) -> The ST Daemon is 
				                          attemping to restore
										  the system from a 
										  previous installation,
										  after an upgrade 
										  attemp failed.
				 error			   (5) -> An error condition.
				                          One or more 
										  components failed
										  to start. More 
										  information can be
										  found from the 
										  Component Table"
            ::= { stdSystemGroup 1 }

	   sysCurrentVersion OBJECT-TYPE
             SYNTAX  DisplayString (SIZE (0..32))
             ACCESS  read-only
             STATUS  mandatory
             DESCRIPTION
                "Specifies the current InstantOffice 
				 version on this system."
            ::= { stdSystemGroup 2 }
     
	 -- The Component Group

     -- Implementation of this group is mandatory for all 
	 -- Vertical InstantOffice systems.  
	 -- This group contains one table: 
	 -- The stdComponentTable 

     stdComponentGroup
       OBJECT IDENTIFIER ::= { selfTestDaemon 2 }


     -- The Component Table 
		
       stdComponentTable OBJECT-TYPE
              SYNTAX  SEQUENCE OF STDComponentEntry
              ACCESS  not-accessible
              STATUS  mandatory
              DESCRIPTION
               "Table of status information about all Instant
			    Office components (executables, services and
				drivers). There are as many entries as there
				are components in the system."
       ::= { stdComponentGroup 1 }

       stdComponentEntry OBJECT-TYPE
             SYNTAX  STDComponentEntry
             ACCESS  not-accessible
             STATUS  mandatory
             DESCRIPTION
              "An entry in the Component table."
             INDEX {compIndex}
             ::= {stdComponentTable 1}
     
       STDComponentEntry ::=
            SEQUENCE {
			  compIndex
                 INTEGER,
              compName
                 DisplayString,
			  compType
				 INTEGER,
			  compInstallStatus     
                 INTEGER,
              compOperStatus
                 INTEGER,
			  compEnabled
				 INTEGER,
			  compLastStart
                 DisplayString
            }


	  compIndex OBJECT-TYPE
              SYNTAX  INTEGER
              ACCESS  read-only
              STATUS  mandatory
              DESCRIPTION
                 "The index of the component"

              ::= { stdComponentEntry 1}

 	  compName OBJECT-TYPE
              SYNTAX  DisplayString (SIZE (0..256))
              ACCESS  read-only
              STATUS  mandatory
              DESCRIPTION
                 "The name of the component"

              ::= { stdComponentEntry 2}

	  compType OBJECT-TYPE
              SYNTAX  INTEGER {
						type-driver			(1),
						type-service		(16),
						type-executable		(2000),
						type-non-vni-driver	(2001),
						type-non-vni-service (2002),
						type-non-vni-executable (2003)
					  }    
              ACCESS  read-only
              STATUS  mandatory
              DESCRIPTION
                 "The Component type - defines whether this 
				  component is a driver, service or an 
				  executable. The following the valid
				  values:
					type-driver	= 1, 
					type-service = 16,
					type-executable = 2000,
					type-non-vni-driver = 2001,
					type-non-vni-service = 2002,
					type-non-vni-executable = 2003"
              ::= { stdComponentEntry 3}

       compInstallStatus OBJECT-TYPE
              SYNTAX  INTEGER {
					uninstalled		 (100), 
					installed          (1)
			  }    
              ACCESS  read-only
              STATUS  mandatory
              DESCRIPTION
                 "Describes the installation status of this 
				  component. The following the valid values:
					uninstalled		  = 100, 
					installed         = 1"
              ::= { stdComponentEntry 4}


       compOperStatus OBJECT-TYPE
              SYNTAX  INTEGER {
					stopped		(1), 
					start-pending	(2),
					stop-pending	(3),
					running		(4),
					continue-pending	(5), 
					pause-pending	(6), 
					paused		(7),
					unknown		(8),
					disabled	(1025) 
					  }    
              ACCESS  read-only
              STATUS  mandatory
              DESCRIPTION
                 "The operational status of this component. 
				  The following the valid
				  values:
					stopped 		=1,
					start-pending	=2,
					stop-pending	=3,
					running 		=4 (the normal operational state),
					continue-pending	=5, 
					pause-pending	=6, 
					paused		=7,
					unknown		=8,
					disabled	=1025"
              ::= { stdComponentEntry 5}

       compEnabled OBJECT-TYPE
              SYNTAX  INTEGER {
						enabled	(100),
						disabled	(1)
					  }    
              ACCESS  read-only
              STATUS  mandatory
              DESCRIPTION
                 "Determines whether this component is 
				  enabled or disabled.
				  Valid values:
					enabled	= 100, 
					disabled    = 1"
              ::= { stdComponentEntry 6}

	  compLastStart OBJECT-TYPE
              SYNTAX  DisplayString (SIZE (0..32))
              ACCESS  read-only
              STATUS  mandatory
              DESCRIPTION
                 "The date-time stamp when this component 
				  was last restarted."

              ::= { stdComponentEntry 7}

-- TRAP Definitions - 

stdCompFailedToStart TRAP-TYPE
	ENTERPRISE  vertical
	VARIABLES {sysCurrentVersion, compName }
	DESCRIPTION
        " This notification is sent when a component fails 
		  to start during initial start-up. "
	::= 26

stdCompAttemptRestart TRAP-TYPE
	ENTERPRISE  vertical
	VARIABLES {sysCurrentVersion, compName }
	DESCRIPTION
        " This notification is sent when the Self Test Daemon
		  attempts to restart a component. "
	::= 27

stdCompFailedToReStart TRAP-TYPE
	ENTERPRISE  vertical
	VARIABLES {sysCurrentVersion, compName }
	DESCRIPTION
        " This notification is sent when an attempt to restart
		  a component failed. "
	::= 28

stdCompRestartComplete TRAP-TYPE
	ENTERPRISE  vertical
	VARIABLES {sysCurrentVersion, compName }
	DESCRIPTION
        " This notification is sent when a component is 
		  successfully restarted "
	::= 29

stdUpgradeStarted TRAP-TYPE
	ENTERPRISE  vertical
	VARIABLES {sysCurrentVersion}
	DESCRIPTION
        "This notification is sent when an InstantOffice 
		 upgrade is started. The stages of an upgrade and 
		 restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"
	::= 30

stdUnpackingFiles TRAP-TYPE
	ENTERPRISE  vertical
	VARIABLES {sysCurrentVersion}
	DESCRIPTION
        "This notification is sent when unpacking of the 
		 upgraded CAB file starts.
		 The stages of an upgrade and restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"

	::= 31

stdUnpackingComplete TRAP-TYPE
	ENTERPRISE  vertical
	VARIABLES {sysCurrentVersion}
	DESCRIPTION
        "This notification is sent when unpacking of the 
		 upgraded CAB file is complete. The stages of an 
		 upgrade and restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"
	::= 32

stdUpgradeBeingApplied TRAP-TYPE
	ENTERPRISE  vertical
	VARIABLES {sysCurrentVersion}
	DESCRIPTION
        "This notification is sent when an InstantOffice
		 upgrade is about to be applied. This is done after
		 the Upgraded CAB file is unpacked and a system
		 reboot is done.
		The stages of an upgrade and restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"
	::= 33

stdUpgradeInProgress TRAP-TYPE
	ENTERPRISE  vertical
	VARIABLES {sysCurrentVersion}
	DESCRIPTION
        " This notification is sent when an InstantOffice 
		  upgrade process is under way. 
		  The stages of an upgrade and restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"
	::= 34


stdUpgradeComplete TRAP-TYPE
	ENTERPRISE  vertical
	VARIABLES {sysCurrentVersion }
	DESCRIPTION
        " This notification is sent when an InstantOffice 
		  upgrade is successfully completed.
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"
	::= 35

stdUpgradeError TRAP-TYPE
	ENTERPRISE  vertical
	VARIABLES {sysCurrentVersion, compName }
	DESCRIPTION
        " This notification is sent when an InstantOffice 
		  upgrade attempt fails. A Restore operation would 
		  be done immediately. 
		  The stages of an upgrade and restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"	
		::= 36

stdRestoreStarted TRAP-TYPE
	ENTERPRISE  vertical
	VARIABLES {sysCurrentVersion }
	DESCRIPTION
        " This notification is sent when a previous version 
		  of InstantOffice is about to be restored. A 
		  restore operation is typically carried out 
		  after a failed upgrade attempt. 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"
	::= 37

stdRestoreInProgress TRAP-TYPE
	ENTERPRISE  vertical
	VARIABLES {sysCurrentVersion }
	DESCRIPTION
        " This notification is sent when a previous version of
		  InstantOffice is restored successfully. A restore 
		  operation is typically carried out after a failed 
		  upgrade attempt. 
		  The stages of an upgrade and restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"	
	::= 38

stdRestoreComplete TRAP-TYPE
	ENTERPRISE  vertical
	VARIABLES {sysCurrentVersion }
	DESCRIPTION
        " This notification is sent when a previous version 
		  of InstantOffice is restored successfully. A 
		  restore operation is typically carried out after 
		  a failed upgrade attempt. 
		  The stages of an upgrade and restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"
	::= 39

stdRestoreError TRAP-TYPE
	ENTERPRISE  vertical
	VARIABLES {sysCurrentVersion }
	DESCRIPTION
        "This notification is sent when an InstantOffice 
		 restore attemp fails.
		The stages of an upgrade and restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"
	::= 40

stdRebootingMachine TRAP-TYPE
	ENTERPRISE  vertical
	VARIABLES {sysCurrentVersion }
	DESCRIPTION
        " This notification is sent before an InstantOffice
		  reboot is done, typically due to an 
		  upgrade/restore request.
		The stages of an upgrade and restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"
	::= 41

stdVerifyingSystem TRAP-TYPE
	ENTERPRISE  vertical
	VARIABLES {sysCurrentVersion }
	DESCRIPTION
        " This notification is sent when the System is brought
		  up (all componenets are started) after an Upgrade or 
		  a restore process.
		The stages of an upgrade and restore are : 
			1. An Upgrade request comes in: CAB file is 
			   pushed - stdUpgradeStarted Trap is sent
			2. Unpacking of the CAB file is done - 
			   stdUnpackingFiles Trap is sent
			3. Multiple stdUpgradeInProgress Traps are sent
			   during this period
			4. Unpacking is complete - stdUnpackingComplete 
			   Trap is sent
			5. A system reboot is done - stdRebootingMachine
			   Trap is sent 
			6. Upgrade is applied - stdUpgradeBeingApplied 
			   Trap is sent.
			7. Multiple stdUpgradeInProgress Traps are sent 
			   during this period
			8. System is rebooted again - stdRebootingMachine
			   Trap is sent.
			9. All components are started - stdVerifyingSystem
			   Trap is sent.
			10. If success: stdUpgradeComplete Trap is sent : 
			    All is well Else ,stdUpgradeError Trap is 
				sent, and a restore operation is attempted 
			11. Restore is attempted - stdRestoreStarted Trap
			    is sent
			12. Multiple stdRestoreInProgress Traps are sent 
			    at this point. 
			13. A system reboot is done : stdRebootingMachine
			    Trap is sent. 
			14. All components are started - stdVerifyingSystem
			    Trap is sent.
			15. If success: stdRestoreComplete Trap is sent,
			    else stdRestoreError Trap is sent. std quits 
				at this point"
	::= 42

stdIOUptoDate TRAP-TYPE
	ENTERPRISE  vertical
	VARIABLES {sysCurrentVersion }
	DESCRIPTION
        " This notification is sent when an upgrade attempt 
		  is aborted because the current version of Instant
		  Office is later than the upgrade version."
	::= 50

stdBadCABFile TRAP-TYPE
	ENTERPRISE  vertical
	VARIABLES {sysCurrentVersion }
	DESCRIPTION
        " This notification is sent when an upgrade attempt 
		  is aborted because of a bad CAB file."
	::= 51

stdNotEnoughDiskSpace TRAP-TYPE
	ENTERPRISE  vertical
	VARIABLES {sysCurrentVersion }
	DESCRIPTION
        " This notification is sent when an upgrade attempt 
		  is aborted because there is not enough disk
		  space on the machine."
	::= 52
 --madhu 11 21 2000 #6472; changed the description
stdIoNotOperational TRAP-TYPE
	ENTERPRISE  vertical
	VARIABLES {sysCurrentVersion, compName  }
	DESCRIPTION
        " This notification is sent under any of the 
		  following conditions:
		  - Before attempting to start the components, FBS 
		    checks to ensure the minimum configuration is 
			present in the box, currently this means  one RSC
			card present in the chassis. If this check fails,
			FBS will not attempt to start any of the components
			and needs to send a trap out to the world!

		  - When FBS attempts to start all components and a 
		    critical component fails to start and hence 
			InstantOffice is not operational, FBS needs to send 
			the trap.

		  - After an upgrade is performed and deemed unsuccessful, 
		    FBS will attempt to restore to the previous working 
			version.  In case this process fails, FBS needs to 
			send the trap."
	::= 63

stdPrerequisiteMissing TRAP-TYPE
	ENTERPRISE  vertical
	VARIABLES {sysCurrentVersion, compName  }
	DESCRIPTION
        " This notification is sent when an upgrade attempt is 
		  done on an InstantOffice that does not contain the 
		  pre-requisite software version for that upgrade."
	
	::= 67

stdPLDFailed TRAP-TYPE
	ENTERPRISE  vertical
	VARIABLES {sysCurrentVersion, compName  }
	DESCRIPTION
        "Resource Card Firmware upgrade failed. 
		 Return code=nnnn"
	
	::= 70

stdUnsupportedConfiguration TRAP-TYPE
	ENTERPRISE  vertical
	VARIABLES {sysCurrentVersion, compName  }
	DESCRIPTION
        "You are running an unsupported configuration.
		 1600-Router card requires a newer version of 
		 the Resource Switch Card."
	
	::= 71

stdInvalidConfiguration TRAP-TYPE
	ENTERPRISE  vertical
	VARIABLES {sysCurrentVersion, compName  }
	DESCRIPTION
        " You are running an invalid configuration. 
		  1600-Router card will be disabled since 
		  there are more than 3 Station Cards present."
	
	::= 72

stdLowDiskSpace TRAP-TYPE
	ENTERPRISE  vertical
	VARIABLES {sysCurrentVersion, compName }
	DESCRIPTION
        "This notification is sent periodically  
		  whenever there is low disk space 
		  space on the machine."
	
		::= 88

stdHardDiskError TRAP-TYPE
	ENTERPRISE  vertical
	VARIABLES {sysCurrentVersion, compName  }
	DESCRIPTION
        "This notification is sent if 
		 there is any disk errors found 
		 during the daily disk checking."
	
		::= 89


stdEventLogError TRAP-TYPE
	ENTERPRISE  vertical
	VARIABLES {sysCurrentVersion, compName }
	DESCRIPTION
        "This notification is sent when there are event mining dll 
		  matching errors found in the event log."
	
		::= 90


END
