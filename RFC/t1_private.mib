VERTICALT1-E1-MIB DEFINITIONS ::= BEGIN

IMPORTS
             Gauge, enterprises
                     FROM RFC1155-SMI
             DisplayString
                     FROM RFC1213-MIB
             OBJECT-TYPE
                     FROM RFC-1212
             TRAP-TYPE
                     FROM RFC-1215;
             

vertical OBJECT IDENTIFIER ::= { enterprises 2338 }  


     --  This MIB module uses the extended OBJECT-TYPE macro as
     --  defined in RFC 1212.
     --   Because this is an extension of rfc1406, the object
     --  prefixes use the string "vdsx1" to reinforce
     --  this relationship.

     --  this is the MIB module for the T1-E1 objects
     --  This MIB is an extension to rfc1406 and contains
     --  Vertical Networks specific variables which facilitate
     --  the management and control of the InstantOffice T1/E1 cards
     --  This MIB is found in the private.enterprise branch of the
     --  MIB tree.

     --  Author  : Dolores Freund
     --  Version : 1.7
     --  Date    : 31 Jul, 2002
     --  Comments : TRACK 15605 : Send SNMP trap when analog loop start trunk 
	 --							  connected/disconnected (traps 86, 87)

     --  Author  : Dolores Freund
     --  Version : 1.6
     --  Date    : 02 Jul, 2002
     --  Comments : TRACK 16397 : Add card types gecko and Python
	 --				TRACK 16402 : Add trunk type coPotsloop
 	 --				TRACK 16403 : enable "other" line coding
	 --				TRACK 5599  : add channel table entries for VDP

  	 --  Author  : Chuck Rosselli
     --  Version : 1.5
     --  Date    : 14 Dec, 1999
	 --  Comments : Added more channel states


  	 --  Author  : Raju Viswambharan
     --  Version : 1.4
     --  Date    : 29 Jan, 1999
	 --  Comments : added more types to ChanhhelType made it 
	 --             read-only since both registry AND database 
	 --             needs to be modified for setting this value


 	 --  Author  : Raju Viswambharan
     --  Version : 1.3
     --  Date    : 10 June, 1998
	 --  Comments : removed all unapplicable options from many items (LineCoding,
	--              Framing, etc)


 	 --  Author  : Raju Viswambharan
     --  Version : 1.2
     --  Date    : 18 May, 1998
	 --  Comments : added vdsx1channelCallerID, vdsx1channelExternalAddress,
	 --				vdsx1channelExternalSubAddress, vdsx1channelLocalAddress
	 --				and  vdsx1channelLocalSubAddress in vdsx1ChannelEntry

	 --  Author  : Raju Viswambharan
     --  Version : 1.1
     --  Date    : 23 Feb, 1998
	 --  Comments : changed the CardTable index to vdsx1cardSlotNumber,
	 --				changed vdsx1TrunkCardIndex to vdsx1TrunkSlotNumber
	 --				changed vdsx1cardISAAddress to vdsx1cardIOPortAddress
	 --			    removed vdsx1cardIndex
	 --				added vdsx1TrunkDeviceNumber
	 --			    renamed vdsx1channelExpectDigitCount to vdsx1channelExtensionLength
	 --			    renamed vdsx1channelCardIndex to vdsx1channelSlotNumber
	 --			    added vdsx1channelExpectDID, vdsx1channelDefaultDestination and vdsx1channelPilotNumber
	 --             added lots of new variables in TrunkTable .
	 --             changed structure of tables to reflect slot-based registry


     --  Author  : Raju Viswambharan
     --  Version : 1.0
     --  Date    : 15 Sept, 1997
	 --  Comments : moved/ removed various variables after discussion
	 --             with Dolores. Changed Trap implementation to snmp
	 --             v1 from v2


     --  Author  : P. Petronelli, PALM Associates, Inc.
     --  Version : 0.0
     --  Date    : 27 August 1997


     vds1    OBJECT IDENTIFIER ::= {vertical 3} 

     -- In order to support multiple T1-E1 cards per system
     -- this MIB has been structured into tables.  The
     -- MIB contains three tables.  In order to correlate all 
     -- three tables, each table contains cross indexes:

     --   T1-E1   card       Which extends the configuration table of
     --                      rfc1406 with Vertical specific parameters.
     --                      There is one row in this table for each card.

     --   T1-E1   trunk      Defines parameters particular to each trunk
     --                      on the above card (s).
     --                      There is one row in this table for each trunk
     --                      on each card.

     --   T1-E1   channel    Defines circuit level characteristics.  There
     --                      is one column in this table for EACH circuit of
     --                      EACH trunk on EACH card defined in the above tables.

     --
     -- 

     -- The card Table

     -- Implementation of this group is mandatory for all Vertical
     -- cards.
     -- The MIB assumes multiple cards are possible.

      -- Implementation of the card group is mandatory for all
      -- InstantOffice systems.  
--bug fixes: #5293, #5405, #5486, #5435, #5790, #5791, #5928, #10030

       vdsx1CardTable OBJECT-TYPE
             SYNTAX  SEQUENCE OF VDsx1CardEntry
             ACCESS  not-accessible
             STATUS  mandatory
             DESCRIPTION
                "The Vertical DS1 Configuration table extension."
            ::= { vds1 1 }

       vdsx1CardEntry OBJECT-TYPE
             SYNTAX  VDsx1CardEntry
             ACCESS  not-accessible
             STATUS  mandatory
             DESCRIPTION
                "An entry in the Vertical Card Configuration
                 table (an extension to the rfc1406 Configuration
                 table."
             INDEX {vdsx1cardSlotNumber}
             ::= {vdsx1CardTable 1}
     
       VDsx1CardEntry ::=
            SEQUENCE {
			  vdsx1cardSlotNumber
				 INTEGER,
              vdsx1cardType
				 INTEGER,
              vdsx1cardDescr
                 INTEGER,
              vdsx1cardRevision
                 INTEGER,
              vdsx1cardDriverVersion
                 INTEGER,
              vdsx1cardIOPortAddress     
                 INTEGER,
              vdsx1cardErrorLED
                 INTEGER,
              vdsx1cardReadyLED
                 INTEGER
            }

         

 	  vdsx1cardSlotNumber OBJECT-TYPE
              SYNTAX  INTEGER (1..14)
              ACCESS  read-only
              STATUS  mandatory
              DESCRIPTION
                 "Physical slot in the system in which the 
				  card is installed."

              ::= { vdsx1CardEntry 1}

  --madhu   11 16 2000 #5435, #5486;    cardTYPE-8-CHANNEL-CO-POTS and  cardTYPE-BRIDGE1 are renamed                                 
  --madhu 11 02 2000 #5407         ;cardTYPE-8-CHANNEL-DID added
  --dmf TRACK 16397 added cardTYPE-GECKO, cardTYPE-PYTHON
	  vdsx1cardType OBJECT-TYPE
              SYNTAX  INTEGER {
						cardTYPE-DUAL-T1                 (1),
--						cardTYPE-24-CHANNEL-STATION      (2),
--			        	cardTYPE-8-CHANNEL-CO-POTS       (3),
						cardTYPE-8-TRUNK                 (3),
--						cardTYPE-BRIDGE1                 (4),
						cardTYPE-RESOURCE-SWITCH-CARD   (4),
--						cardTYPE-12-CHANNEL-STATION      (6),
--						cardTYPE-WAN1                    (7),
--						cardTYPE-24-RIB                  (10),
                        cardTYPE-8-CHANNEL-DID           (13), 
						cardTYPE-DNI								(22),
						cardTYPE-GECKO					 (24),
						cardTYPE-PYTHON					 (25),
						cardTYPE-8-CHANNEL-ANALOG-UNIVERSAL (29),
                        cardTYPE-NOT-CONFIGURED          (100)
					  }    
              ACCESS  read-only
              STATUS  mandatory
--added DID by madhu 11 02 2000 #5407
--dmf TRACK 16397 added cardTYPE-GECKO, cardTYPE-PYTHON
              DESCRIPTION
                 "The Vertical's card Type. The following types are defined:
					cardTYPE-DUAL-T1                 = 1,
					cardTYPE-8-TRUNK                 = 3,
					cardTYPE-RESOURCE-SWITCH-CARD    = 4,
                    cardTYPE-8-CHANNEL-DID           = 13, 
					cardTYPE-DNI								= 22, 
					cardTYPE-GECKO					 = 24,
					cardTYPE-PYTHON					 = 25,
					cardTYPE-8-CHANNEL-ANALOG-UNIVERSAL = 29,
					cardTYPE-NOT-CONFIGURED          = 100 "
              ::= { vdsx1CardEntry 2}

      vdsx1cardDescr OBJECT-TYPE
              SYNTAX  INTEGER (0..255)
              ACCESS  read-only
              STATUS  mandatory
              DESCRIPTION
                 "Vertical card identification number."

              ::= { vdsx1CardEntry 3}


      vdsx1cardRevision OBJECT-TYPE
              SYNTAX  INTEGER (0..255)
              ACCESS  read-only
              STATUS  mandatory
              DESCRIPTION
                 "Vertical card revision level."

              ::= { vdsx1CardEntry 4}


      vdsx1cardDriverVersion OBJECT-TYPE
              SYNTAX  INTEGER (0..255)
              ACCESS  read-only
              STATUS  mandatory
              DESCRIPTION
                 "Vertical card driver version."

              ::= { vdsx1CardEntry 5}


       vdsx1cardIOPortAddress OBJECT-TYPE
             SYNTAX  INTEGER (0..'7fffffff'h)
             ACCESS  read-only
             STATUS  mandatory
             DESCRIPTION
                "The ISA bus base address for this Card."

            ::= { vdsx1CardEntry  6}


      vdsx1cardErrorLED OBJECT-TYPE
              SYNTAX  INTEGER (0..1)
              ACCESS  read-only
              STATUS  mandatory
              DESCRIPTION
                 "All Vertical cards have an ERROR LED and
                  a READY LED.  The combined values of these
                  LEDs are as follows -
                  ERRORLed    READYLed VALUE OPERATIONAL DEFINITION
                  OFF         OFF      (0 0) Invalid state  
                  ON          OFF      (1 0) Just after power up. This state 
                                             remains until card is 
                                              ready to service io.
                  ON          ON       (1 1) Statue during software initialization 
                  OFF         ON       (0 1) The normal operational state
                                              of the card."

              ::=  { vdsx1CardEntry 7}



       vdsx1cardReadyLED OBJECT-TYPE
              SYNTAX INTEGER (0..1)
              ACCESS  read-only
              STATUS  mandatory
              DESCRIPTION
                   "All Vertical cards have a READY LED and
                    an ERROR LED.  The combined values of these
                    LEDs are as follows -
                    ERRORLed    READYLed  OPERATIONAL DEFINITION
                    OFF         OFF       invalid state
                    ON          OFF       Just after power up. This 
                                          state remains until card is 
                                          ready to service io.
                    ON          ON        Statue during software initialization
                    OFF         ON        The normal operational state of the card."

              ::=  { vdsx1CardEntry 8}



        --  End of card group

  --  Vertical Networks Trunk Group
  --  There is one trunk group for each T1/E1 trunk
  --  on a specific card.


  -- The  Vertical Trunk Table
  -- This group is a table, one entry for each
  -- trunk supported on this card.  Each row in the
  -- table is indexed and contains a cross index to the
  -- card upon which this trunk is implemented.

  -- The following are extensions to the DS1 Configuration Table
  -- found in rfc1406 (also supported by the InstantOffice
  -- Management Framework).


      vdsx1TrunkTable OBJECT-TYPE
             SYNTAX  SEQUENCE OF VDsx1TrunkEntry
             ACCESS  not-accessible
             STATUS  mandatory
             DESCRIPTION
                "The DS1 Trunk table extensions for 
                 Vertical Networks InstantOffice."
            ::= { vds1 2 }
    
        vdsx1TrunkEntry OBJECT-TYPE
             SYNTAX    VDsx1TrunkEntry
             ACCESS    not-accessible
             STATUS    mandatory
             DESCRIPTION 
                  "An entry in the Vertical DS1 Trunk table"
             INDEX     { vdsx1TrunkIfIndex }
             ::=       { vdsx1TrunkTable 1 }

         VDsx1TrunkEntry ::=
              SEQUENCE {
             vdsx1TrunkIfIndex
                 INTEGER,
             vdsx1TrunkIndex
                 INTEGER,
             vdsx1TrunkIdentifier
                 DisplayString,
             vdsx1TrunkSlotNumber
                  INTEGER,
			 vdsx1TrunkDeviceNumber
				  INTEGER,
			 vdsx1TrunkInterrupt
				  INTEGER,
			 vdsx1TrunkEnabled       
                 INTEGER,
			 vdsx1TrunkMasterPriority
				 INTEGER,
			 vdsx1TrunkStream             
                 INTEGER,
             vdsx1TrunkStartingChannel              
                 INTEGER,
			 vdsx1TrunkType
				 INTEGER,
			 vdsx1TrunkIsdnSignalingProtocol
				 INTEGER,
			 vdsx1TrunkLineCoding
				 INTEGER,
			 vdsx1TrunkFraming
				 INTEGER,
			 --vdsx1TrunkDChannelSlot
			--	 INTEGER,
			-- vdsx1TrunkDChannelDevice
			--	 INTEGER,
			 vdsx1TrunkNumberOfChannels
				 INTEGER,
			 vdsx1TrunkLineBuildOut
				 INTEGER,
			 vdsx1TrunkLoopback
				 INTEGER,
			 vdsx1TrunkRedLED
				 INTEGER,
			 vdsx1TrunkYellowLED
				 INTEGER,
--TRACK 13415 dmf 07/12/02 remove:			 vdsx1TrunkChangePending
--				 INTEGER,
--12 18 2000 madhu #4971				 
		     vdsx1TrunkLOSThreshold
		         INTEGER,
		     vdsx1TrunkTransmitPulseMask
		         INTEGER,
             vdsx1TrunkReceiveEqualizer
                 INTEGER
         }

         vdsx1TrunkIfIndex OBJECT-TYPE
             SYNTAX  INTEGER (1..'7fffffff'h)
             ACCESS  read-only
             STATUS  mandatory
             DESCRIPTION
                "The interface Index for this trunk. The value for this object  
				 is  equal  to  the value  of  dsx1IfIndex from the Interfaces 
				 table of DS1/E1 (RFC 1406).  Which also correlates to the
                 IfIndex found in MIB-II."

            ::= { vdsx1TrunkEntry 1 }


         vdsx1TrunkIndex OBJECT-TYPE
             SYNTAX  INTEGER (1..'7fffffff'h)
             ACCESS  read-only
             STATUS  mandatory
             DESCRIPTION
                "This object is the index into the number
                 of trunks associated with the card defined
                 in the card group."
                
            ::= { vdsx1TrunkEntry 2 }


        vdsx1TrunkIdentifier OBJECT-TYPE
             SYNTAX DisplayString (SIZE (0..255))
             ACCESS  read-only
             STATUS  mandatory
             DESCRIPTION
                "This value for this object  is  equal  to  the
                value  of  dsx1CircuitIdentifier
                from the Configuration table of
                DS1/E1 (RFC 1406).  This is a vendor specific
                field used to help identify each specific
                interface for diagnostic purposes."

            ::= { vdsx1TrunkEntry 3 }


         vdsx1TrunkSlotNumber OBJECT-TYPE
             SYNTAX INTEGER (0..255)
             ACCESS  read-only
             STATUS  mandatory
             DESCRIPTION
                "The value for this object is the
                  logical number of the slot in which the 
				  card containing this trunk is located, (vdsx1cardSlotNumber)."

            ::= { vdsx1TrunkEntry 4 }

         vdsx1TrunkDeviceNumber OBJECT-TYPE
             SYNTAX INTEGER (0..255)
             ACCESS  read-only
             STATUS  mandatory
             DESCRIPTION
                "The value for this object is the logical device number of 
				 this trunk within its slot. This number may be used to 
				 identify this device in the registry."

            ::= { vdsx1TrunkEntry 5 }

		vdsx1TrunkInterrupt OBJECT-TYPE
             SYNTAX  INTEGER (1..2147483647)
             ACCESS  read-only
             STATUS  mandatory
             DESCRIPTION
                "Interrupt Request level for this card/trunk. 
                 Note: all trunks in the same card have the same IRQ.  "

            ::= { vdsx1TrunkEntry 6 }


      vdsx1TrunkEnabled OBJECT-TYPE
             SYNTAX  INTEGER {
					 vdsx1TrunkActivated (1),
					vdsx1TrunkNotConfigured(2),
					vdsx1TrunkDeactivated (100)
                     }
             ACCESS  read-only
             STATUS  mandatory
             DESCRIPTION
                "Setting this variable to Deactivated will
                 disable this particular trunk. "

            ::= { vdsx1TrunkEntry 7}
--12 04 2000 madhu #5293

	  vdsx1TrunkMasterPriority OBJECT-TYPE
              SYNTAX  INTEGER {
					 primary (1),
                     secondary (2),
					 --firstAlternate (2),
					 --secondAlternate (3),
					 notUsed (100),
					 notApplicable (200)
                     	}

              ACCESS  read-only
              STATUS  mandatory
              DESCRIPTION
                 "Designates the priority for selecting
				  which trunk is to drive the MVIP SEC8K
				  clock, i.e. which trunk drives the master
				  timing system. This value must be diffrent 
				  for each Trunk in the system.Valid values 
				  mean:
					notUsed (100)=> never choose this trunk as clock master
					primary (1)=> choose this trunk as first choice
					secondary (2) => choose this trunk as second choice
					notApplicable (200) => Master Priority is not applicable to this type of trunk."
              ::=  { vdsx1TrunkEntry 8 }


     vdsx1TrunkStream OBJECT-TYPE
             SYNTAX  INTEGER (0..7)
             ACCESS  read-only
             STATUS  mandatory
             DESCRIPTION
                "The MVIP Stream assigned to the Trunk."

            ::= { vdsx1TrunkEntry 9 }


    vdsx1TrunkStartingChannel OBJECT-TYPE
             SYNTAX  INTEGER (0..24)
             ACCESS  read-only
             STATUS  mandatory
             DESCRIPTION
                "The starting MVIP channel within the MVIP Stream.
				 If CardType is DTM or WAN1, this value is 0; if
				 CardType is CO-POTS, this value is 16 or 24."

            ::= { vdsx1TrunkEntry 10 }
        --12 18 2000 madhu #5436 ;  dev-CSU-DSU(16) added
-- dmf TRACK 16402 - added dev-coPotsLoop
	vdsx1TrunkType OBJECT-TYPE
              SYNTAX  INTEGER {
					dev-t1CAS (1),
					dev-t1CCS (2),
--					dev-t1CCSnoD (3),
--					dev-e1CAS (4),
--					dev-e1CCS (5),
--					dev-e1CCSnoD (6),
					dev-coPots (7),
--					dev-station (8),
--					dev-DSPMgr (9),
--					dev-RicRes (10),
--					dev-RicRIB (11),
--					dev-Switch (12),
--					dev-HDLCMgr (13),
--					dev-56KCSM (14),
--					dev-Audio (15),
                    dev-CSU-DSU(16),
					dev-Serial-DNI(42),
					dev-coPotsLoop (49),
					dev-AUM (50),
					dev-undef (100)
				}
              ACCESS  read-only
              STATUS  mandatory
-- dmf TRACK 16402 - added dev-coPotsLoop
              DESCRIPTION
                 "Specifies the TrunkType for this trunk.
				  Defines E1 vs T1 as well as Common 
				  Channel Signalling (CCS) vs. Channel
				  Associated Signalling (CAS). Valid values 
				  are :
					dev-undef,			//  100 : undefined
					dev-t1CAS,			//  1 : T1 Channel Associated Signaling
					dev-t1CCS,			//  2 : T1 Common Channel Signaling : with D channel
					dev-coPots,			//  7 : CO Pots (analog),
					dev-CSU-DSU,		//  16: CSU/DSU card,
					dev-Serial-DNI,	    //  42: Serial Device on DNI card
					dev-coPotsLoop,		//  49: CO Pots (analog), loop start only
					dev-AUM,			//  50: AUM card"
              ::=  { vdsx1TrunkEntry 11}

--	vdsx1TrunkNetworkSide OBJECT-TYPE
--             SYNTAX  INTEGER (0..1)
--              ACCESS  read-write
--              STATUS  mandatory
--              DESCRIPTION
--                 "Defines whether the PRI signalling will
--				  play the role of the network side or the 
--				  user side of the protocol. Valid values -
--				  0 => User side,
--				  1 => network side."
--            ::=  { vdsx1TrunkEntry 12}

           -- 11 30 2000 madhu #5789; other is replaced by not-aplicable & invalid
           -- more values added as "invalid" since driver is supporting and if it is returning the un-supported 
           -- values by SNMP should disply "invalid"
	vdsx1TrunkIsdnSignalingProtocol OBJECT-TYPE
              SYNTAX      INTEGER {
               	notUsed(0),			 -- not supported
               	invalid(1),          -- not in range
               	
               	invalid(2),          -- dss1
               	invalid(3),          --etsi  
               	invalid(4),          --dass2
               	invalid(8),          --dms250
               	invalid(9),          --nil
               	invalid(11),         --ni3
               	invalid(12),         --vn2
               	invalid(13),         --vn3
               	invalid(14),         --vn4
               	invalid(15),         --vn6
               	invalid(16),         --kdd
               	invalid(17),         --ins64
               	invalid(18),         --ins1500
               	invalid(19),         --itr6
               	invalid(20),         --cornet
               	invalid(21),         --ts013
               	invalid(22),         --ts014
               	invalid(23),         --qsig
               	invalid(24),         --swissnet2
               	invalid(25),         --swissnet3
            	ess4(5),            -- U.S.A. / AT&T 4ESS
             	ess5(6),            -- U.S.A. / AT&T 5ESS
             	dms100(7),          -- U.S.A. / Northern Telecom DMS100
             	ni2(10),            -- U.S.A. / National ISDN 2 (BRI, PRI)
				dms100s100 (263),	-- NT DMS-100 switch / S-100
				notApplicable (200) -- Not aplicable.
        	}

              ACCESS  read-only
              STATUS  mandatory
              DESCRIPTION
                 "Defines the switch type for the Isdn
			protocol stack. The following are all the 
			possible types:
			    notUsed(0),   Not a supported configuration
			    invalid,             Not in range
	            ess4(5),             U.S.A. / AT&T 4ESS
             	ess5(6),             U.S.A. / AT&T 5ESS
             	dms100(7),           U.S.A. / Northern Telecom DMS100
             	ni2(10),             U.S.A. / National ISDN 2 (BRI, PRI)
				dms100s100 (263),	 NT DMS-100 switch / S-100
				notApplicable (200)  Not applicable for this type of trunk"
              ::=  { vdsx1TrunkEntry 12}

--	vdsx1TrunkPhysicalDCE OBJECT-TYPE
--              SYNTAX  INTEGER {
--					DTE (0),
--					DCE (1)
--				}
--              ACCESS  read-write
--              STATUS  mandatory
--              DESCRIPTION
--                 "Defines whether the physical ISDN link is DTE (0)
--				  or DCE (1)."
--              ::=  { vdsx1TrunkEntry 14}
--
--	vdsx1TrunkDataLinkDCE OBJECT-TYPE
--              SYNTAX  INTEGER {
--					DTE (0),
--					DCE (1)
--				}
--              ACCESS  read-write
--              STATUS  mandatory
--              DESCRIPTION
--                 "Defines whether the logical ISDN link is DTE (0)
--				  or DCE (1)."
--              ::=  { vdsx1TrunkEntry 15}
--01 12 2001 madhu #5767; other removed
--dmf TRACK 16403 enable option 6
	vdsx1TrunkLineCoding OBJECT-TYPE
              SYNTAX  INTEGER {
--					jbzs (1),
					b8zs (2),
--					hdb3 (3),
--					zbtsi (4),
					ami  (5),
					other (6),
					notApplicable (200)
				}
              ACCESS  read-only
              STATUS  mandatory
              DESCRIPTION
                 "Line Coding, i.e. the zero code suppression
		  used for this Trunk. Valid values are:
		  b8ZS (2) ->  use of a specified  pattern  of  
			       normal  bits  and  bipolar violations
                	       which are used to replace a sequence  
			       of  eight zero bits.
		  aMI (5)  ->  a mode wherein no  zero  code suppression  
			       is  present
		  other (6) -> none of the codes described above, or Not 
				 Applicable, whichever is appropriate
		  notApplicable (200) -> Not applicable for this type of trunk.

		  Presently, T1 trunk can be either
		  b8zs (2) or ami (5). 
		  E1 trunk must be hdb3 (3)."
              ::=  { vdsx1TrunkEntry 13}

	vdsx1TrunkFraming OBJECT-TYPE
              SYNTAX  INTEGER {
					other  (1),
					esf    (2),
					d4     (3),
					notApplicable (200)
--					e1-crc (5),
--					e1-mf  (6)
				}
              ACCESS  read-only
              STATUS  mandatory
              DESCRIPTION
                 "Defines framing for Trunk. T1 trunk can be either esf (2)
				  or d4 (3). E1 trunk can be either e1-crc (5) or e1-mf (6).
			In cases where Framing is not applicable, value 1 (other) or 
			more likely 200 (notApplicable)  would 
  			be displayed."
              ::=  { vdsx1TrunkEntry 14}


--madhu 11 21 2000 #5790 removing the access

--	vdsx1TrunkDChannelSlot OBJECT-TYPE
--             SYNTAX  INTEGER (1..18)
--             ACCESS  read-write
--             STATUS  mandatory
--             DESCRIPTION
--                 "Slot number of trunk whose DChannel controls the B channels 
--			  of this trunk. "
--              ::=  { vdsx1TrunkEntry 15}

--madhu 11 03 2000 #5791 removing the access

--	vdsx1TrunkDChannelDevice OBJECT-TYPE
  --            SYNTAX  INTEGER (1..9)
    --          ACCESS  read-write
      --        STATUS  mandatory
        --      DESCRIPTION
          --       "Specifies the device number of the trunk
		--		  whose D channel controls the B channels 
	--   	  of this trunk. "
           --   ::=  { vdsx1TrunkEntry 16}

	vdsx1TrunkNumberOfChannels OBJECT-TYPE
              SYNTAX  INTEGER (0..24)
              ACCESS  read-only
              STATUS  mandatory
              DESCRIPTION
                 "Maximum number of channels to be 
				  initialized for this trunk - 
				  0..24 for T1, 
				  0..31 for E1,
				  0..8  for COPots."
              ::=  { vdsx1TrunkEntry 17}

-- 	vdsx1TrunkLoopLength OBJECT-TYPE  renamed to vdsx1TrunkLineBuildOut - bug 3286
--notApplicable replaced by custom; madhu 11 10 2000 #5924 ; again its comming back !!!!!! :)
-- 07/10/02 dmf TRACK 4030 : SNMP T1 private agent: For CO-POTS & Resource Switch , 
--             MIB Variable "vdsx1TrunkLineBuildOut" value should be "Not applicabe" 

	vdsx1TrunkLineBuildOut OBJECT-TYPE
              SYNTAX  INTEGER {
						buildOut-minus7point5dB (1),
						buildOut-minus15dB (2),
						buildOut-minus22point5dB(3),
						buildOut-0dB   (100), 
						buildOut-notApplicable (200)
					}
              ACCESS  read-only
              STATUS  mandatory
              DESCRIPTION
				"Defines the line build out option. The following are applicable
				 values :
				         buildOut-0dB   (100),
						 buildOut-minus7point5dB (1),
						 buildOut-minus15dB (2),
						 buildOut-minus22point5dB(3),
						 buildOut-notApplicable (200)"
              ::=  { vdsx1TrunkEntry 18}

--	vdsx1TrunkLOSThreshold OBJECT-TYPE
--              SYNTAX  INTEGER (0..2147483647)
--              ACCESS  read-write
--              STATUS  mandatory
--              DESCRIPTION
--                 "Loss of Signal Threshold. This value need not be specified.
--				  Its value is indirectly defined by vdsx1TrunkLoopLength. "
--              ::=  { vdsx1TrunkEntry 22}
--
--	vdsx1TrunkLineBuildOut OBJECT-TYPE
--              SYNTAX  INTEGER (0..2147483647)
--              ACCESS  read-write
--              STATUS  mandatory
--              DESCRIPTION
--                 "Line Build Out. This value need not be specified.
--				  Its value is indirectly defined by vdsx1TrunkLoopLength. "
--              ::=  { vdsx1TrunkEntry 23}
--
--	vdsx1TrunkTransmitPulseMask OBJECT-TYPE
--              SYNTAX  INTEGER (0..2147483647)
--              ACCESS  read-write
--              STATUS  mandatory
--              DESCRIPTION
--                 "Transmit Pulse Mask. This value need not be specified.
--				  Its value is indirectly defined by vdsx1TrunkLoopLength."
--              ::=  { vdsx1TrunkEntry 24}
--
--	vdsx1TrunkReceiveEqualizer OBJECT-TYPE
--              SYNTAX  INTEGER (0..2147483647)
--              ACCESS  read-write
--              STATUS  mandatory
--              DESCRIPTION
--                 "Receive Equalizer. This value need not be specified.
--				  Its value is indirectly defined by vdsx1TrunkLoopLength."
--              ::=  { vdsx1TrunkEntry 25}
--
	vdsx1TrunkLoopback OBJECT-TYPE
              SYNTAX  INTEGER {
                         vdsx1NoLoop(1),
                         vdsx1PayloadLoop(2),
                         vdsx1LineLoop(3),
                         vdsx1OtherLoop(4),
						 notApplicable (200)
                     }
             ACCESS  read-only
             STATUS  mandatory
             DESCRIPTION
                "This variable represents the  loopback  confi-
                guration of the DS1 interface.  Agents support-
                ing read/write access should return badValue in
                response to a requested loopback state that the
                interface does not support.  The values mean:

                vdsx1NoLoop
                     Not in the loopback state.  A device  that
                     is not capable of performing a loopback on
                     the interface shall always return this  as
                     it's value.

                vdsx1PayloadLoop
                     The received signal at this  interface  is
                     looped  through  the device. Typically the
                     received signal is  looped  back  for  re-
                     transmission  after  it has passed through
                     the device's framing function.

                vdsx1LineLoop
                     The received signal at this interface does
                     not  go  through the device (minimum pene-
                     tration) but is looped back out.

                vdsx1OtherLoop
                     Loopbacks that are not defined here.

				notApplicable (200)
					 Loopback not applicable in this type of trunk."
              ::=  { vdsx1TrunkEntry 19}

--	vdsx1TrunkTimerValue0 OBJECT-TYPE
--              SYNTAX  INTEGER (0..2147483647)
--              ACCESS  read-write
--              STATUS  mandatory
--              DESCRIPTION
--                 "Loss of Frame allignment duration (in milliseconds) 
--				  before Red Alarm. "
--              ::=  { vdsx1TrunkEntry 27}
--
--	vdsx1TrunkTimerValue1 OBJECT-TYPE
--              SYNTAX  INTEGER (0..2147483647)
--              ACCESS  read-write
--              STATUS  mandatory
--              DESCRIPTION
--                 "Carrier Frame Alarm clear interval (in milliseconds). "
--              ::=  { vdsx1TrunkEntry 28}
--

	vdsx1TrunkRedLED OBJECT-TYPE
              SYNTAX  INTEGER (0..1)
              ACCESS  read-only
              STATUS  mandatory
              DESCRIPTION
                 " Specifies the RED LED status of the trunk 
				    OFF = 0,
					ON = 1."
              ::=  { vdsx1TrunkEntry 20}
	
	vdsx1TrunkYellowLED OBJECT-TYPE
              SYNTAX  INTEGER (0..1)
              ACCESS  read-only
              STATUS  mandatory
              DESCRIPTION
                 " Specifies the YELLOW LED status of the trunk 
				    OFF = 0,
					ON = 1."
              ::=  { vdsx1TrunkEntry 21}

--TRACK 13415 dmf 07/12/02 remove vdsx1TrunkChangePending
--	vdsx1TrunkChangePending OBJECT-TYPE
--             SYNTAX  INTEGER (0..1)
--             ACCESS  read-only
--             STATUS  mandatory
--            DESCRIPTION
--               "Indicates that a change to the device
--				  values have been made to the registry.
--				  The intepretation of the values are :
--				  1 => change made to the registry, but 
--				       not incorporated in the device yet
--				  0 => the device changes the value to 0
--				        from 1, after it incorporates the 
--						value from registry."
--              ::=  { vdsx1TrunkEntry 22}  
              
--12 18 2000 madhu #4971				 
          
    vdsx1TrunkLOSThreshold OBJECT-TYPE
              SYNTAX  INTEGER {
              
              
    				lOS1point36    (0),				-- 1.36 volts	
					lOS1point04    (1),				-- 1.04 volts	
					lOS0point84    (2),				-- 0.84 volts	
					lOS0point62    (3),				-- 0.62 volts	
					lOS0point43    (4),				-- 0.43 volts	
					lOS0point32    (5),				-- 0.32 volts	
					lOS0point22    (6),				-- 0.22 volts	
					lOS-NOT-IN-USE (7),			    -- 7
					notApplicable (200)				-- 200
			}

              ACCESS  read-only
              STATUS  mandatory
              DESCRIPTION
                 "Loss of Signal Threshold. Its value is indirectly defined 
                 by vdsx1TrunkLoopLength.               
                  	lOS1point36    (0),			
					lOS1point04    (1),			
					lOS0point84    (2),			
					lOS0point62    (3),			
					lOS0point43    (4),			
					lOS0point32    (5),			
					lOS0point22    (6),			
					lOS_NOT_IN_USE (7),
					notApplicable (200)"
                 
              ::=  { vdsx1TrunkEntry 23}
              
 	vdsx1TrunkTransmitPulseMask OBJECT-TYPE
              SYNTAX  INTEGER (0..16777215)
              ACCESS  read-only
              STATUS  mandatory
              DESCRIPTION
                 "Transmit Pulse Mask.Its value is indirectly defined by vdsx1TrunkLoopLength. A value 
				  of 200 should be interpreted as notApplicable, meaning in the case of thid type of trunk,
				  the Transmit pulse mask is not applicable."
              ::=  { vdsx1TrunkEntry 24}

	vdsx1TrunkReceiveEqualizer OBJECT-TYPE
			SYNTAX  INTEGER {
              		FALSE    (0),				
					TRUE    (1),
					notApplicable (200) 		
			}
              ACCESS  read-only
              STATUS  mandatory
              DESCRIPTION
                 "Receive Equalizer.Its value is indirectly defined 
                 by vdsx1TrunkLoopLength.
                 0 -> FALSE,
                 1 -> TRUE 
				 200 -> notApplicable. "
              ::=  { vdsx1TrunkEntry 25}




--  The Vertical Card table extensions
--  to the rfc1406 MIB for the channels.

--  Each Trunk can have up to 24 (T1) or
--  32 (E1) channels.  This is a three dimensional
--  array packed into the standard two dimensional
--  MIB Table.  Each channel has a reference to
--  the Trunk to which it is associated, in addition
--  to its own index within the trunk.


     --madhu 11 16 2000 #5928
     --vdsx1ChannelEnabled,vdsx1ChannelState,vdsx1ChannelCallerID,vdsx1ChannelExternalAddress
     --vdsx1ChannelExternalSubAddress,vdsx1ChannelLocalAddress,vdsx1ChannelLocalSubAddress
     --made to read only

	 --dmf TRACK 5599 : add vdsx1channelUseFDT, vdsx1channelCollectDigitCount, vdsx1channelProvideTones

   vdsx1ChannelTable OBJECT-TYPE
       SYNTAX SEQUENCE OF VDsx1ChannelEntry
       ACCESS not-accessible
       STATUS mandatory
       DESCRIPTION
             "Channel entries for each of the
              channels associated with each trunk
              defined in the trunk table."

      ::= { vds1 9 }

  vdsx1ChannelEntry OBJECT-TYPE
       SYNTAX VDsx1ChannelEntry
       ACCESS not-accessible
       STATUS mandatory
       DESCRIPTION
              "Each entry is one channel in a T1/E1 trunk."

       INDEX  {vdsx1TrunkIfIndex, vdsx1channelIndex }
       ::=  { vdsx1ChannelTable 1 }


  VDsx1ChannelEntry ::=
       SEQUENCE {
		vdsx1channelIndex
            INTEGER,
		vdsx1channelTrunkIndex
            INTEGER,
		vdsx1channelSlotNumber
			INTEGER,
		vdsx1channelTrunkDeviceNumber
			INTEGER,
		vdsx1channelEnabled
            INTEGER,
		vdsx1channelType
            INTEGER,
		vdsx1channelState
			INTEGER,
		vdsx1channelCallerID
			DisplayString,
		vdsx1channelExternalAddress
			DisplayString,
		vdsx1channelExternalSubAddress
			DisplayString,
		vdsx1channelLocalAddress
			DisplayString,
		vdsx1channelLocalSubAddress
			DisplayString,
--TRACK 13415 dmf 07/12/02 remove:		vdsx1channelChangePending
--            INTEGER,
		vdsx1channelUseFDT
			INTEGER,
		vdsx1channelCollectDigitCount
			INTEGER,
		vdsx1channelProvideTones
			INTEGER
}

    vdsx1channelIndex  OBJECT-TYPE
             SYNTAX  INTEGER (1..32)
             ACCESS  read-only
             STATUS  mandatory
             DESCRIPTION
                "This is the logical channel number of the
                 channel within its trunk.  For T1 it is between 1 and 24
                 for E1 it is between 1 and 32. "

            ::= { vdsx1ChannelEntry 1}


    vdsx1channelTrunkIndex  OBJECT-TYPE
             SYNTAX  INTEGER (0..255)
             ACCESS  read-only
             STATUS  mandatory
             DESCRIPTION
                "This is the index of the trunk (relative to 
				 its card) to which this channel belongs."

            ::= { vdsx1ChannelEntry 2}


	vdsx1channelSlotNumber OBJECT-TYPE
             SYNTAX INTEGER (0..255)
             ACCESS  read-only
             STATUS  mandatory
             DESCRIPTION
                "The value for this object is the
                  logical number of the slot in which the 
				  card (and trunk) containing is located (vdsx1cardSlotNumber).."

            ::= { vdsx1ChannelEntry 3 }

	vdsx1channelTrunkDeviceNumber OBJECT-TYPE
             SYNTAX INTEGER (0..255)
             ACCESS  read-only
             STATUS  mandatory
             DESCRIPTION
                "The value for this object is the logical device number of 
				 the trunk containing this channel within its slot, 
				 ie vdsx1TrunkDeviceNumber "

            ::= { vdsx1ChannelEntry 4 }


    -- vdsx1channelNotConfigured commented out by madhu 11 10 2000 #5813
    vdsx1channelEnabled  OBJECT-TYPE
             SYNTAX  INTEGER {
                      vdsx1channelActivated (1),         
					  --  vdsx1channelNotConfigured (2),   
					  vdsx1channelDeactivated (100)
                      }
            -- ACCESS  read-write
             ACCESS  read-only
             STATUS  mandatory
             DESCRIPTION
                "Setting this variable to Deactivated will disable
                 this particular channel. Valid values are :
			vdsx1channelDeactivated (100)
			vdsx1channelActivated (1)	
			vdsx1channelNotConfigured (2)"

            ::= { vdsx1ChannelEntry 5}



    vdsx1channelType  OBJECT-TYPE
             SYNTAX  INTEGER {
		    vdsx1channelTypeWink  (2),
                    vdsx1channelTypeGS    (5),
		    vdsx1channelTypeClear (6),
		    vdsx1channelTypeAnalogImm (7),
		    vdsx1channelTypeBChan (8),
		    vdsx1channelTypeDChan (9),
		    vdsx1channelTypeAnalogDt (11),
			vdsx1channelTypeAnalogGs (12),
			vdsx1channelTypeDDS (13),
			vdsx1channelTypeAnalogDID (14),
			vdsx1channelTypeUnknown (100)
                   }
             ACCESS  read-only
             STATUS  mandatory
             DESCRIPTION
                "Channel type, 
      		   vdsx1channelTypeUnknown : Unknown type
                   vdsx1channelTypeWink  : E&M (Ear and Mouth) start
                   vdsx1channelTypeGS    : Ground Start Digital trunk.
		   vdsx1channelTypeClear : Nailed up clear channel, for data
		   vdsx1channelTypeAnalogImm: Analog Trunk, Immediate start
		   vdsx1channelTypeBChan:  PRI B channel on T1 or E1
		   vdsx1channelTypeDChan:  PRI D channel on T1 or E1 
		   vdsx1channelTypeAnalogDt: Analog channel, dialtone start
		   vdsx1channelTypeAnalogGs: Analog channel, ground start
		   vdsx1channelTypeDDS: DDS channel (56K or 64K)
		   vdsx1channelTypeAnalogDID: Analog channel, DID wink"

            ::= { vdsx1ChannelEntry 6}

--	vdsx1channelStripDigitCount  OBJECT-TYPE
--             SYNTAX  INTEGER (0..32)
--             ACCESS  read-write
--             STATUS  mandatory
--             DESCRIPTION
--                " The number of digits to be stripped 
--				  from the incoming digits. "
--            
--             ::= { vdsx1ChannelEntry 7 }
--
--	vdsx1channelPrefixDigits  OBJECT-TYPE
--             SYNTAX DisplayString (SIZE (0..32))
--             ACCESS  read-write
--             STATUS  mandatory
--             DESCRIPTION
--                " Prefix digit string to report on incoming call. "
--            
--             ::= { vdsx1ChannelEntry 8 }
--
--	vdsx1channelDefaultDestination  OBJECT-TYPE
--             SYNTAX DisplayString (SIZE (0..32))
--             ACCESS  read-write
--             STATUS  mandatory
--             DESCRIPTION
--                " The digit string which should replace the dialed
--				  digits received in the following cases:
--				  - Insufficient digits received
--				  - The digits received match the PilotNumber. "
--            
--             ::= { vdsx1ChannelEntry 9 }
--
--    vdsx1channelPilotNumber  OBJECT-TYPE
--             SYNTAX DisplayString (SIZE (0..32))
--             ACCESS  read-write
--             STATUS  mandatory
--             DESCRIPTION
--                " The digit string which typically represents the 
--				  pilot number of an incoming trunk group. A match 
--				  on this number will result in the call being 
--				  directed to the DefaultDestination. "
--            
--             ::= { vdsx1ChannelEntry 10 }
--
--    vdsx1channelExtensionLength  OBJECT-TYPE
--             SYNTAX  INTEGER (0..32)
--             ACCESS  read-write
--             STATUS  mandatory
--             DESCRIPTION
--                " Number of digits the connection manager is expecting
--				  on an incoming call indication. This includes the 
--				  number of digits specified in PrefixDigits. For non-DID
--				  trunk, this number is equal to the number of digits in 
--				  PrefixDigits."
--
--            ::= { vdsx1ChannelEntry 11}
--
--	vdsx1channelExpectDID  OBJECT-TYPE
--             SYNTAX  INTEGER (0..1)
--             ACCESS  read-write
--             STATUS  mandatory
--             DESCRIPTION
--                " Designates whether or not DID digit
--				  collection should be enabled for each 
--				  incoming call.
--				  0 => if no digits to be collected.
--				  1 => if DID digits may be collected."
--            
--             ::= { vdsx1ChannelEntry 12 }

    vdsx1channelState  OBJECT-TYPE
             SYNTAX  INTEGER {
					channelStateOOS (1),
					channelStateIdle (2),
					channelStateInCall (3),
					channelStateOutCall (4),
					channelStateOffline (5),
					channelStateOther (6),
					channelStateData (7),
					channelStateError (8),
					channelStateFeRinging (9),
					channelStateNeRinging (10),
					channelStateDigitSend (11),
					channelStateDigitRcv (12),
					channelStateIncallEst (13),
					channelStateOutcallEst (14),
					channelStateIncallClear (15),
					channelStateOutcallClear (16),
					 channelStateDchanDown (17),
					channelStateBchanDown (18),
					channelStateTrunkLoop (19),
					channelStateInitializing (20),
					channelStateRemoved (255)
			 }
             --ACCESS  read-write
             ACCESS  read-only
             STATUS  mandatory
             DESCRIPTION
                " The Call State of this particular channel.
				  Valid values are :
					Out of Service (channelStateOOS - 1),
					Idle (channelStateIdle - 2),
					InBound Call (channelStateInCall - 3),
					OutBound Call (channelStateOutCall - 4),
					Off line (channelStateOffline - 5),
					Other state (channelStateOther - 6),
					Data (channelStateData - 7),
					Error (channelStateError - 8),
					Ringing Far End (channelStateFeRinging - 9),
					Incoming Ringing (channelStateNeRinging - 10),
					Sending Digits (channelStateDigitSend - 11),
					Receiving Digits (channelStateDigitRcv - 12),
					Incall Established (channelStateIncallEst - 13),
					Outcall Established (channelStateOutcallEst - 14),
					Incall Clearing (channelStateIncallClear - 15),
					Outcall Clearing (channelStateOutcallClear - 16),
					Associated D-channel (layer 2) is down (channelStateDchanDown -17),
					 Channel is down at layer 3 due to PRI problems (channelStateBchanDown - 18),
					Channel is unuseable due to trunk test loop (channelStateTrunkLoop- 19),
					 Channel is currently coming up (channelStateInitializing - 20),
					Channel is currently removed as a valid analog station port (channelStateRemoved - 255)."

            ::= { vdsx1ChannelEntry 7}

    vdsx1channelCallerID  OBJECT-TYPE
             SYNTAX DisplayString (SIZE (0..32))
             --ACCESS  read-write
             ACCESS  read-only
             STATUS  mandatory
             DESCRIPTION
                " The callerID of an incoming caller, if available. If the callerID is
             	not available, then it will have a length of zero"
            
             ::= { vdsx1ChannelEntry 8 }

    vdsx1channelExternalAddress  OBJECT-TYPE
             SYNTAX DisplayString (SIZE (0..32))
             --ACCESS  read-write
             ACCESS  read-only
             STATUS  mandatory
             DESCRIPTION
                " The far end number of a connected call on this channel.If the number is
             	not available, then it will have a length of zero." 
            
             ::= { vdsx1ChannelEntry 9 }

    vdsx1channelExternalSubAddress  OBJECT-TYPE
             SYNTAX DisplayString (SIZE (0..32))
             --ACCESS  read-write
             ACCESS  read-only
             STATUS  mandatory
             DESCRIPTION
                " The far end sub address of a connected call on this channel.If this is
             	not available, then it will have a length of zero"
            
             ::= { vdsx1ChannelEntry 10 }

    vdsx1channelLocalAddress  OBJECT-TYPE
             SYNTAX DisplayString (SIZE (0..32))
             --ACCESS  read-write
             ACCESS  read-only
             STATUS  mandatory
             DESCRIPTION
                " The local number of a connected call on this channel.If the number is
             	not available, then it will have a length of zero"
            
             ::= { vdsx1ChannelEntry 11 }

    vdsx1channelLocalSubAddress  OBJECT-TYPE
             SYNTAX DisplayString (SIZE (0..32))
             --ACCESS  read-write
             ACCESS  read-only
             STATUS  mandatory
             DESCRIPTION
                " The local sub address of a connected call on this channel.If the number is
             	not available, then it will have a length of zero"
            
             ::= { vdsx1ChannelEntry 12 }


 --   vdsx1channelTimerValue0  OBJECT-TYPE
 --            SYNTAX  INTEGER (1..'7fffffff'h)
 --            ACCESS  read-write
 --            STATUS  mandatory
 --            DESCRIPTION
 --               "Channel timer : dtmf tone duration"
 --
 --          ::= { vdsx1ChannelEntry 19}
--
--
--    vdsx1channelTimerValue1  OBJECT-TYPE
--             SYNTAX  INTEGER (1..'7fffffff'h)
--             ACCESS  read-write
--             STATUS  mandatory
--             DESCRIPTION
--                "Channel timer : verify incoming off-hook"
--
--            ::= { vdsx1ChannelEntry 20}
--
--    vdsx1channelTimerValue2  OBJECT-TYPE
--             SYNTAX  INTEGER (1..'7fffffff'h)
--             ACCESS  read-write
--             STATUS  mandatory
--             DESCRIPTION
--                "Channel timer : duration of transmit wink"
--
--            ::= { vdsx1ChannelEntry 21}
--    vdsx1channelTimerValue3  OBJECT-TYPE
--             SYNTAX  INTEGER (1..'7fffffff'h)
--             ACCESS  read-write
--            STATUS  mandatory
 --            DESCRIPTION
 --               "Channel timer : time to wait before dialing
--				                 digits"
--
--            ::= { vdsx1ChannelEntry 22}
--
--    vdsx1channelTimerValue4  OBJECT-TYPE
--             SYNTAX  INTEGER (1..'7fffffff'h)
--             ACCESS  read-write
--             STATUS  mandatory
--             DESCRIPTION
--                "Channel timer : max time to wait for digit
--								 collection"
--
--            ::= { vdsx1ChannelEntry 23}
--
--    vdsx1channelTimerValue5  OBJECT-TYPE
--             SYNTAX  INTEGER (1..'7fffffff'h)
--             ACCESS  read-write
--             STATUS  mandatory
 --            DESCRIPTION
 --               "Channel timer : max time to wait for incoming
--								 off-hook"
--
 --           ::= { vdsx1ChannelEntry 24}
--
--    vdsx1channelTimerValue6  OBJECT-TYPE
--             SYNTAX  INTEGER (1..'7fffffff'h)
--             ACCESS  read-write
--             STATUS  mandatory
--             DESCRIPTION
 --               "Channel timer : min duration to receive wink"
--            ::= { vdsx1ChannelEntry 25}
--
--    vdsx1channelTimerValue7  OBJECT-TYPE
--             SYNTAX  INTEGER (1..'7fffffff'h)
--             ACCESS  read-write
--             STATUS  mandatory
--             DESCRIPTION
--                "Channel timer : max duration to receive wink"
--
--            ::= { vdsx1ChannelEntry 26}
--
--    vdsx1channelTimerValue8  OBJECT-TYPE
--             SYNTAX  INTEGER (1..'7fffffff'h)
--             ACCESS  read-write
--             STATUS  mandatory
 --            DESCRIPTION
 --               "Channel timer : delay when no digits expected"
--
--            ::= { vdsx1ChannelEntry 27}
--
--    vdsx1channelTimerValue9  OBJECT-TYPE
--             SYNTAX  INTEGER (1..'7fffffff'h)
 --            ACCESS  read-write
 --            STATUS  mandatory
--             DESCRIPTION
--                "Channel timer : min off-hook to validate
--								 answer of outbound call"
--
--            ::= { vdsx1ChannelEntry 28}
--
--    vdsx1channelTimerValue10  OBJECT-TYPE
--             SYNTAX  INTEGER (1..'7fffffff'h)
--             ACCESS  read-write
--             STATUS  mandatory
--             DESCRIPTION
--                "Channel timer : max wait for answer of outbound
--								 call."
--
--            ::= { vdsx1ChannelEntry 29}
--
--    vdsx1channelTimerValue11  OBJECT-TYPE
--             SYNTAX  INTEGER (1..'7fffffff'h)
--             ACCESS  read-write
--             STATUS  mandatory
--             DESCRIPTION
--                "Channel timer : Inbound call, we hang up first,
--								 max wait rcv on-hook"
--
--            ::= { vdsx1ChannelEntry 30}
--
--    vdsx1channelTimerValue12 OBJECT-TYPE
--             SYNTAX  INTEGER (1..'7fffffff'h)
--             ACCESS  read-write
--             STATUS  mandatory
--             DESCRIPTION
--                "Channel timer : Inbound call, we hang up first,
--								 validate rcv on-hook"
--
--            ::= { vdsx1ChannelEntry 31}
--
--    vdsx1channelTimerValue13  OBJECT-TYPE
--             SYNTAX  INTEGER (1..'7fffffff'h)
--             ACCESS  read-write
--             STATUS  mandatory
 --            DESCRIPTION
 --               "Channel timer : Inbound call, validate on-hook"
--
--            ::= { vdsx1ChannelEntry 32}
--    vdsx1channelTimerValue14  OBJECT-TYPE
--             SYNTAX  INTEGER (1..'7fffffff'h)
--             ACCESS  read-write
--             STATUS  mandatory
--             DESCRIPTION
--                "Channel timer : Outbound call, we hang up first,
--								 max wait rcv on-hook"
--
--            ::= { vdsx1ChannelEntry 33}
--
--    vdsx1channelTimerValue15  OBJECT-TYPE
--             SYNTAX  INTEGER (1..'7fffffff'h)
--             ACCESS  read-write
 --            STATUS  mandatory
 --            DESCRIPTION
 --               "Channel timer : Outbound call, we hang up first,
--								 min wait for next outbound call."
--
--            ::= { vdsx1ChannelEntry 34}
--
--    vdsx1channelTimerValue16  OBJECT-TYPE
--             SYNTAX  INTEGER (1..'7fffffff'h)
--             ACCESS  read-write
--             STATUS  mandatory
--             DESCRIPTION
--                "Channel timer : Outbound call,validate on-hook"
--
--            ::= { vdsx1ChannelEntry 35}
--
--    vdsx1channelTimerValue17  OBJECT-TYPE
--             SYNTAX  INTEGER (1..'7fffffff'h)
--             ACCESS  read-write
--             STATUS  mandatory
--             DESCRIPTION
--                "Channel timer : Parameter 17"
--            ::= { vdsx1ChannelEntry 36}
--
--    vdsx1channelTimerValue18  OBJECT-TYPE
--             SYNTAX  INTEGER (1..'7fffffff'h)
--             ACCESS  read-write
--             STATUS  mandatory
--             DESCRIPTION
--                "Channel timer : Parameter 18"
--
--            ::= { vdsx1ChannelEntry 37}
--
--    vdsx1channelTimerValue19  OBJECT-TYPE
--             SYNTAX  INTEGER (1..'7fffffff'h)
--             ACCESS  read-write
--             STATUS  mandatory
--             DESCRIPTION
--                "Channel timer : Parameter 19"
--
--            ::= { vdsx1ChannelEntry 38}

--TRACK 13415 dmf 07/12/02 remove:	vdsx1channelChangePending  OBJECT-TYPE
--             SYNTAX  INTEGER (0..1)
--             ACCESS  read-only
--             STATUS  mandatory
--             DESCRIPTION
--				"Indicates that a change to the channel
--				  values have been made to the registry.
--				  The intepretation of the values are :
--				  1 => change made to the registry, but 
--				       not incorporated in the device yet
--				  0 => the device changes the value to 0
--				        from 1, after it incorporates the 
--						value from registry."            
--            ::= { vdsx1ChannelEntry 13 }

	vdsx1channelUseFDT  OBJECT-TYPE
             SYNTAX  INTEGER (0..1)
             ACCESS  read-only
             STATUS  mandatory
             DESCRIPTION
				"Indicates whether or not the First Digit Table 
				  should be referenced when collecting digits
				  for an incoming call.
				  The intepretation of the values are :
				  1 => reference the First Digit Table
				  0 => collect the number of digits indicated
					    by vdsx1channelCollectDigitCount."
             ::= { vdsx1ChannelEntry 14 }

	vdsx1channelCollectDigitCount  OBJECT-TYPE
             SYNTAX  INTEGER (0..32)
             ACCESS  read-only
             STATUS  mandatory
             DESCRIPTION
				"Indicates the number of digits to collect 
				  for incoming calls when vdsx1channelUseFDT is 0."
             ::= { vdsx1ChannelEntry 15 }

	vdsx1channelProvideTones  OBJECT-TYPE
             SYNTAX  INTEGER (0..1)
             ACCESS  read-only
             STATUS  mandatory
             DESCRIPTION
				"Indicates whether or not to provide dialtone 
				  prior to collecting digits for an incoming call.
				  The intepretation of the values are :
				  1 => provide dialtone.
						typically used in tandem configurations.
				  0 => do not provide dialtone."
             ::= { vdsx1ChannelEntry 16 }

-- TRAP Definitions

-- These TRAPS are associated with a specific trunk.
-- Only the most significant cases are used for traps, 
-- specifically when a trunk goes into a RED, YELLOW or BLUE
-- situation.

vdsx1TrunkRedClear TRAP-TYPE
	ENTERPRISE  vertical
	VARIABLES {vdsx1TrunkIdentifier, vdsx1cardSlotNumber , vdsx1TrunkDeviceNumber, vdsx1TrunkIndex }
	DESCRIPTION
		" This notification is sent when the specific
          trunk RED alarm condition clears. "
	::= 1

vdsx1TrunkRed TRAP-TYPE
	ENTERPRISE  vertical
	VARIABLES {vdsx1TrunkIdentifier, vdsx1cardSlotNumber , vdsx1TrunkDeviceNumber, vdsx1TrunkIndex }
	DESCRIPTION
        " This notification is sent when the specific
          trunk goes into the RED alarm situation. Red 
	    alarm condition signifies LOS (Loss of Signal)
	    failure, i.e. the receiver sees no positive or
	    negative pulses"
	::= 2

vdsx1TrunkYellowClear TRAP-TYPE
	ENTERPRISE  vertical
	VARIABLES {vdsx1TrunkIdentifier, vdsx1cardSlotNumber , vdsx1TrunkDeviceNumber, vdsx1TrunkIndex }
	DESCRIPTION
        " This notification is sent when the specific
          trunk YELLOW alarm condition clears. "
	::= 3 

vdsx1TrunkYellow TRAP-TYPE
	ENTERPRISE  vertical
	VARIABLES { vdsx1TrunkIdentifier, vdsx1cardSlotNumber , vdsx1TrunkDeviceNumber, vdsx1TrunkIndex }
	DESCRIPTION
		" This notification is sent when the specific
              trunk goes into the YELLOW alarm situation. 
		  Yellow alarm condition signifies a LOF (Loss
		  of Frame) condition, i.e. the receiver does not
   		  see the expected framing pattern."
	::= 4 

vdsx1TrunkBlueClear TRAP-TYPE
	ENTERPRISE  vertical
	VARIABLES {vdsx1TrunkIdentifier, vdsx1cardSlotNumber , vdsx1TrunkDeviceNumber, vdsx1TrunkIndex }
	DESCRIPTION
		" This notification is sent when the specific
          trunk BLUE alarm condition clears. "
	::= 5

vdsx1TrunkBlue TRAP-TYPE
	ENTERPRISE  vertical
	VARIABLES {vdsx1TrunkIdentifier, vdsx1cardSlotNumber , vdsx1TrunkDeviceNumber, vdsx1TrunkIndex }
	DESCRIPTION
		" This notification is sent when the specific
          trunk goes into the BLUE alarm situation. Blue alarm
	    conditions occurs when the source goes into AIS (Alarm
	    indication Signal) state. This means that the source has
	    a problem that prevents it from sending its normal, framed
	    payload. Instead, it sends an unframed stream of 1's."
	::= 6

vdsx1TrunkReconfigComplete TRAP-TYPE
	ENTERPRISE  vertical
	VARIABLES {vdsx1TrunkIdentifier, vdsx1cardSlotNumber , vdsx1TrunkDeviceNumber, vdsx1TrunkIndex }
	DESCRIPTION
        " This notification is sent when the specific
          trunk successfully reads and incorporates the
	    values from the registry. This is typically done 
	    in response to a SET command on any of the Trunk's (or
	    its channel's) read-write parameters"
	::= 7

vdsx1TrunkReconfigError TRAP-TYPE
	ENTERPRISE  vertical
	VARIABLES {vdsx1TrunkIdentifier, vdsx1cardSlotNumber , vdsx1TrunkDeviceNumber, vdsx1TrunkIndex }
	DESCRIPTION
        " This notification is sent when the specific
          trunk fails to incorporate the values read from
	    the registry. Typically, the trunk tries to re-read 
	    the registry values in response to a SET command on 
	    any of the Trunk's (or its channel's) read-write parameters"
	::= 8

vdsx1TrunkLoopbackPayloadOn TRAP-TYPE
	ENTERPRISE  vertical
	VARIABLES {vdsx1TrunkIdentifier, vdsx1cardSlotNumber , vdsx1TrunkDeviceNumber, vdsx1TrunkIndex }
	DESCRIPTION
		" This notification is sent when the specific
          trunk enters a payload loopback state. Payload loopback means that
		  the received signal at this  interface  is looped  through  the 
		  device. Typically the received signal is  looped  back  for  re-
          transmission  after  it has passed through the device's framing function"
	::= 43
vdsx1TrunkLoopbackPayloadOff TRAP-TYPE
	ENTERPRISE  vertical
	VARIABLES {vdsx1TrunkIdentifier, vdsx1cardSlotNumber , vdsx1TrunkDeviceNumber, vdsx1TrunkIndex }
	DESCRIPTION
		" This notification is sent when the specific
          trunk moves from a payload loopback state to a 
		  non loopback state."
	::= 44
vdsx1TrunkLoopbackLineOn TRAP-TYPE
	ENTERPRISE  vertical
	VARIABLES {vdsx1TrunkIdentifier, vdsx1cardSlotNumber , vdsx1TrunkDeviceNumber, vdsx1TrunkIndex }
	DESCRIPTION
		" This notification is sent when the specific
          trunk enters a line loopback state. Under this state the received 
		  signal at this interface does not  go  through the device 
		  (minimum penetration) but is looped back out."
	::= 45
vdsx1TrunkLoopbackLineOff TRAP-TYPE
	ENTERPRISE  vertical
	VARIABLES {vdsx1TrunkIdentifier, vdsx1cardSlotNumber , vdsx1TrunkDeviceNumber, vdsx1TrunkIndex }
	DESCRIPTION
		" This notification is sent when the specific
          trunk goes out of a Line Looped state"
	::= 46
vdsx1TrunkAnalogDisconnect TRAP-TYPE
	ENTERPRISE  vertical
	VARIABLES {vdsx1cardSlotNumber , vdsx1TrunkDeviceNumber, vdsx1TrunkIndex, vdsx1TrunkIdentifier }
	DESCRIPTION
		" This notification is sent when the specific
          analog trunk is disconnected"
	::= 86
vdsx1TrunkAnalogConnect TRAP-TYPE
	ENTERPRISE  vertical
	VARIABLES {vdsx1cardSlotNumber , vdsx1TrunkDeviceNumber, vdsx1TrunkIndex, vdsx1TrunkIdentifier }
	DESCRIPTION
		" This notification is sent when the specific
          analog trunk is connected"
	::= 87
vdsx1EnterChannelErrorState TRAP-TYPE
	ENTERPRISE  vertical
	VARIABLES {vdsx1cardSlotNumber , vdsx1TrunkDeviceNumber, vdsx1TrunkIndex, vdsx1TrunkIdentifier }
	DESCRIPTION
		" This notification is sent when unexpected signaling is detected 
		  on a T1 channel or analog trunk.  While in this state, the T1 
		  channel or analog trunk is out of service"
	::= 91

END
