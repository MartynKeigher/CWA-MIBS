XEROX-HOST-RESOURCES-EXT-TC DEFINITIONS ::= BEGIN

--  Module: Host Resources Extensions Textual Conventions
--  Author: Ira McDonald, Alan Sullivan, Rob Westfall
--  File:   10hosttc.mib
--  Date:   14 December 1997 - Version 2.40.pub

--  Textual Conventions companion to the Host Resources Extensions MIB
--  Contains the REGISTRY of XCMI Standard Device Types,
--  the REGISTRY of XCMI Standard CRU Types,
--  the REGISTRY of XCMI HRX Admin Service Types, and
--  the REGISTRY of XCMI HRX Admin Device Operation Types.

IMPORTS
    MODULE-IDENTITY, OBJECT-IDENTITY,
        OBJECT-TYPE
            FROM SNMPv2-SMI             -- IETF RFC 1442/1902
    TEXTUAL-CONVENTION
            FROM SNMPv2-TC              -- IETF RFC 1443/1903
    xeroxCommonMIB
            FROM XEROX-COMMON-MIB;

xcmHrTC MODULE-IDENTITY
    LAST-UPDATED "9712140000Z"
    ORGANIZATION "Xerox Corporation - XCMI Working Group"
    CONTACT-INFO
        "           XCMI Editors
        Email:      xcmieditors@cp10.es.xerox.com

        --
        --
        "
    DESCRIPTION
        "Version:    2.40.pub

        The TC module for textual conventions, enumerated types, OIDs,
        and other volatile elements of the companion Host Resources
        Extensions MIB ('xcmHrMIB'), which supports extended
        configuration and management of various host resources for
        network accessible host systems.  These modules augment and
        extend the original IETF Host Resources MIB (RFC 1514).

        Usage:  This MIB module introduces support for the 'realization'
        of both 'physical' and 'logical' devices, consistent with ISO
        DPA (Document Printing Application), ISO/IEC 10175, as reflected
        in the object 'xcmHrDevInfoRealization'.

        Note:   Conforming implementations shall NOT 'bubble up' status
        from 'physical' devices to associated 'logical' devices.  All
        devices shall ALWAYS report their own status ONLY.

        Copyright (C) 1997 Xerox Corporation. All Rights Reserved."
    ::= { xeroxCommonMIB 52 }

--
--          The Host Resources Extensions (HRX) TC
--

--          REGISTRY of XCMI Standard Device Types
--          (used with 'hrDeviceType' in Device Group
--          of the IETF Host Resources MIB, RFC 1514).
--
--  Usage:  Developers should ALWAYS request registration of appropriate
--  XCMI standard device types when they design or integrate a device
--  (ALWAYS with some physical, and not merely logical, realization)
--  which is network manageable on a host system.
--
--  Usage:  Logical devices (ie, services of some sort) should ALWAYS
--  be represented by: a) their own fully free-standing MIBs; and/or
--  b) elaboration of an existing IETF or XCMI standard device type into
--  a 'logical' sibling.
--
--  The final arc of IETF standard device types is ALWAYS within the
--  range '1..99'.
--  The final arc of XCMI standard device types is ALWAYS within the
--  range '101..199'.
--
--  In the future, XCMI may add types for 'marker', 'input tray', etc,
--  to enable support of managed host systems which do NOT have printer


--  capabilities (and therefore do NOT implement the IETF Printer MIB
--  MIB), and to support installation and configuration information for
--  their component physical subunits.

xcmHrDeviceTypes OBJECT-IDENTITY
    STATUS      current
    DESCRIPTION
        "The root of all additional device types defined in HRX TC."
    ::= { xcmHrTC 2 }

xcmHrDeviceHostSystem OBJECT-IDENTITY
    STATUS      current
    DESCRIPTION
        "Host system device type - manufacturer independent.
        For host systems which instrument multiple devices and
        support MIBs with tables INDEXed by 'hrDeviceIndex', the single
        'xcmHrDeviceHostSystem' device represents the 'root' device
        which may be used to manage overall host system defaults,
        configuration, status, etc."
    ::= { xcmHrDeviceTypes 101 }

xcmHrDeviceScanner OBJECT-IDENTITY
    STATUS      current
    DESCRIPTION
        "Scanner device type - manufacturer independent.
        An 'xcmHrDeviceScanner' device with 'xcmHrDevInfoRealization' of
        'physical' is a 'real' input device (eg, a 'scan channel' on a
        multifunction printer).
        An 'xcmHrDeviceScanner' device with 'xcmHrDevInfoRealization' of
        'logical' is a 'virtual' input device (eg, a 'personality' of a
        'scan channel' on a multifunction printer)."
    ::= { xcmHrDeviceTypes 102 }

xcmHrDeviceCopier OBJECT-IDENTITY
    STATUS      current
    DESCRIPTION
        "Copier device type - manufacturer independent.
        An 'xcmHrDeviceCopier' device with 'xcmHrDevInfoRealization' of
        'physical' is a 'real' I/O device (eg, a 'copier' on a
        multifunction printer).
        An 'xcmHrDeviceCopier' device with 'xcmHrDevInfoRealization' of
        'logical' is a 'virtual' I/O device (eg, a 'personality' of a
        'copier' on a multifunction printer)."
    ::= { xcmHrDeviceTypes 103 }

xcmHrDeviceFax OBJECT-IDENTITY
    STATUS      current
    DESCRIPTION
        "Fax device type - manufacturer independent.
        An 'xcmHrDeviceFax' device with 'xcmHrDevInfoRealization' of
        'physical' is a 'real' I/O device (eg, a 'fax channel' on a
        multifunction printer).
        An 'xcmHrDeviceFax' device with 'xcmHrDevInfoRealization' of
        'logical' is a 'virtual' I/O device (eg, a 'personality' of a


        'fax channel' on a multifunction printer)."
    ::= { xcmHrDeviceTypes 104 }

xcmHrDeviceMailbox OBJECT-IDENTITY
    STATUS      current
    DESCRIPTION
        "Mailbox device type - manufacturer independent.
        An 'xcmHrDeviceMailbox' device is a 'multi-bin' output device.
        An 'xcmHrDeviceMailbox' device with 'xcmHrDevInfoRealization' of
        'physical' is a 'real' output device (eg, a 'tower mailbox' on
        a high-end printer).
        An 'xcmHrDeviceMailbox' device with 'xcmHrDevInfoRealization' of
        'logical' is a 'virtual' output device (eg, a 'personality' of a
        'tower mailbox' on a high-end printer)."
    ::= { xcmHrDeviceTypes 105 }

xcmHrDeviceFinisher OBJECT-IDENTITY
    STATUS      current
    DESCRIPTION
        "Finisher device type - manufacturer independent.
        An 'xcmHrDeviceFinisher' device is an output finishing device.
        An 'xcmHrDeviceFinisher' device with 'xcmHrDevInfoRealization'
        of 'physical' is a 'real' output device (eg, a 'stapler'
        on a high-end printer).
        An 'xcmHrDeviceFinisher' device with 'xcmHrDevInfoRealization'
        of 'logical' is a 'virtual' output device (eg, a 'personality'
        of a 'stapler' on a high-end printer)."
    ::= { xcmHrDeviceTypes 106 }

--          REGISTRY of XCMI Standard CRU Types
--          (used with 'hrDeviceType' in Device Group
--          of the IETF Host Resources MIB, RFC 1514).

xcmHrCruXerographicModule OBJECT-IDENTITY
    STATUS      current
    DESCRIPTION
        "CRU xerographic module - manufacturer independent.
        An 'xcmHrCruXerographicModule' device is a customer
        replaceable unit, with 'xcmHrDevInfoRealization' of 'physical'."
    ::= { xcmHrDeviceTypes 201 }

xcmHrCruFuserModule OBJECT-IDENTITY
    STATUS      current
    DESCRIPTION
        "CRU fuser module - manufacturer independent.
        An 'xcmHrCruFuserModule' device is a customer
        replaceable unit, with 'xcmHrDevInfoRealization' of 'physical'."
    ::= { xcmHrDeviceTypes 202 }

xcmHrCruTonerBottleModule OBJECT-IDENTITY
    STATUS      current
    DESCRIPTION
        "CRU toner bottle module - manufacturer independent.
        An 'xcmHrCruTonerBottleModule' device is a customer


        replaceable unit, with 'xcmHrDevInfoRealization' of 'physical'."
    ::= { xcmHrDeviceTypes 203 }

xcmHrCruCollectorBottleModule OBJECT-IDENTITY
    STATUS      current
    DESCRIPTION
        "CRU (developer) collector bottle - manufacturer independent.
        An 'xcmHrCruCollectorBottleModule' device is a customer
        replaceable unit, with 'xcmHrDevInfoRealization' of 'physical'."
    ::= { xcmHrDeviceTypes 204 }

xcmHrCruTrayFeedHeadModule OBJECT-IDENTITY
    STATUS      current
    DESCRIPTION
        "CRU tray feed head module - manufacturer independent.
        An 'xcmHrCruTrayFeedHeadModule' device is a customer
        replaceable unit, with 'xcmHrDevInfoRealization' of 'physical'."
    ::= { xcmHrDeviceTypes 205 }

xcmHrCruAdfFeedHeadModule OBJECT-IDENTITY
    STATUS      current
    DESCRIPTION
        "CRU ADF feed head module - manufacturer independent.
        An 'xcmHrCruAdfFeedHeadModule' device is a customer
        replaceable unit, with 'xcmHrDevInfoRealization' of 'physical'.
        Note:   ADF is an acronym for 'automatic document feeder'."
    ::= { xcmHrDeviceTypes 206 }

--          REGISTRY of XCMI HRX Admin Service Types (Classes)
--          (MAY be used in the 'xcmSec[Service|PolicyService]TypeOID'
--          objects in the closely related XCMI Security MIB, in
--          conforming management agents which do NOT implement the
--          related XCMI System Admin MIB).

xcmHrAdminServiceTypes OBJECT-IDENTITY
    STATUS      current
    DESCRIPTION
        "The root of all host system management service types (classes)
        defined in the Host Resources Extensions TC."
    REFERENCE
        "See:   'XcmSecPosixVerbs' and 'xcmSecServiceTypeOID'
                in XCMI Security TC/MIB."
    ::= { xcmHrTC 3 }

xcmHrAdminObjectService OBJECT-IDENTITY
    STATUS      current
    DESCRIPTION
        "The host system object management service."
    REFERENCE
        "See:   'xcmSysAdminObject...' in XCMI System Admin MIB.
        See:    'XcmSecPosixVerbs' and 'xcmSecServiceTypeOID'
                in XCMI Security TC/MIB."
    ::= { xcmHrAdminServiceTypes 1 }


xcmHrAdminServerService OBJECT-IDENTITY
    STATUS      current
    DESCRIPTION
        "The host system server management service."
    REFERENCE
        "See:   'xcmSysAdminServer...' in XCMI System Admin MIB,
                'hrSW[Running|Installed]Table' in IETF HR MIB, and
                'xcmHrSW[Running|Installed]ExtTable' in XCMI HRX MIB.
        See:    'XcmSecPosixVerbs' and 'xcmSecServiceTypeOID'
                in XCMI Security TC/MIB."
    ::= { xcmHrAdminServiceTypes 2 }

xcmHrAdminDeviceService OBJECT-IDENTITY
    STATUS      current
    DESCRIPTION
        "The host system device management service."
    REFERENCE
        "See:   'xcmSysAdminDevice...' in XCMI System Admin MIB,
                'hrDeviceTable' in IETF HR MIB, and
                'xcmHrDev[Info|Help|Mgmt|Power|Traffic|Calendar]Table'
                in XCMI HRX MIB.
        See:    'XcmSecPosixVerbs' and 'xcmSecServiceTypeOID'
                in XCMI Security TC/MIB."
    ::= { xcmHrAdminServiceTypes 3 }

xcmHrAdminJobService OBJECT-IDENTITY
    STATUS      current
    DESCRIPTION
        "The host system job management service."
    REFERENCE
        "See:   'xcmSysAdminJob...' in XCMI System Admin MIB, and
                'xcmJob[...]Table' in XCMI Job Monitoring MIB.
        See:    'XcmSecPosixVerbs' and 'xcmSecServiceTypeOID'
                in XCMI Security TC/MIB."
    ::= { xcmHrAdminServiceTypes 4 }

xcmHrAdminDocService OBJECT-IDENTITY
    STATUS      current
    DESCRIPTION
        "The host system document management service."
    REFERENCE
        "See:   'xcmSysAdminDoc...' in XCMI System Admin MIB, and
                'xcmDoc[...]Table' in XCMI Job Monitoring MIB.
        See:    'XcmSecPosixVerbs' and 'xcmSecServiceTypeOID'
                in XCMI Security TC/MIB."
    ::= { xcmHrAdminServiceTypes 5 }

xcmHrAdminSecurityService OBJECT-IDENTITY
    STATUS      current
    DESCRIPTION
        "The host system security management service."
    REFERENCE
        "See:   'xcmSysAdminSecurity...' in XCMI System Admin MIB.


        See:    'XcmSecPosixVerbs' and 'xcmSecServiceTypeOID'
                in XCMI Security TC/MIB."
    ::= { xcmHrAdminServiceTypes 6 }

xcmHrAdminCommsService OBJECT-IDENTITY
    STATUS      current
    DESCRIPTION
        "The host system communications management service."
    REFERENCE
        "See:   'xcmSysAdminComms...' in XCMI System Admin MIB and
                XCMI Comms Config and Comms Engine MIBs.
        See:    'XcmSecPosixVerbs' and 'xcmSecServiceTypeOID'
                in XCMI Security TC/MIB."
    ::= { xcmHrAdminServiceTypes 7 }

--          REGISTRY of XCMI HRX Admin Device Operation Types
--          (MAY be used in the 'xcmSecPolicyVerbTypeOID'
--          object in the closely related XCMI Security MIB, for
--          fine-grained access control to device management verbs, in
--          conforming management agents which do NOT implement the
--          related XCMI System Admin MIB).

xcmHrAdminDeviceOperationTypes OBJECT-IDENTITY
    STATUS      current
    DESCRIPTION
        "The root of all host resources admin device operation types
        defined in the Host Resources Extensions TC.

        Usage:  The following OIDs support access control for the simple
        device admin operations defined in 'XcmHrDevMgmtCommandRequest'
        and used in 'xcmHrDevMgmtCommandRequest' in the XCMI HRX MIB,
        via 'xcmSec[Master|Policy]VerbTypeOID' in the XCMI Security MIB,
        WITHOUT requiring implementation of the XCMI System Admin MIB."
    REFERENCE
        "See:   'xcmSec[Master|Policy]VerbTypeOID' in
                XCMI Security MIB."
    ::= { xcmHrTC 4 }

xcmHrAdminDeviceNone            OBJECT IDENTIFIER
    ::= { xcmHrAdminDeviceOperationTypes 1 }
xcmHrAdminDeviceStartup         OBJECT IDENTIFIER
    ::= { xcmHrAdminDeviceOperationTypes 2 }
xcmHrAdminDeviceResetWarning    OBJECT IDENTIFIER
    ::= { xcmHrAdminDeviceOperationTypes 3 }
xcmHrAdminDeviceTest            OBJECT IDENTIFIER
    ::= { xcmHrAdminDeviceOperationTypes 4 }
xcmHrAdminDeviceShutdown        OBJECT IDENTIFIER
    ::= { xcmHrAdminDeviceOperationTypes 5 }
xcmHrAdminDeviceQuiesce         OBJECT IDENTIFIER
    ::= { xcmHrAdminDeviceOperationTypes 6 }
xcmHrAdminDeviceResetCounters   OBJECT IDENTIFIER
    ::= { xcmHrAdminDeviceOperationTypes 7 }
xcmHrAdminDeviceResetWarm       OBJECT IDENTIFIER
    ::= { xcmHrAdminDeviceOperationTypes 8 }


xcmHrAdminDeviceResetCold       OBJECT IDENTIFIER
    ::= { xcmHrAdminDeviceOperationTypes 9 }
xcmHrAdminDeviceResetFactory    OBJECT IDENTIFIER
    ::= { xcmHrAdminDeviceOperationTypes 10 }
xcmHrAdminDeviceFlushInput      OBJECT IDENTIFIER
    ::= { xcmHrAdminDeviceOperationTypes 11 }
xcmHrAdminDeviceFlushOutput     OBJECT IDENTIFIER
    ::= { xcmHrAdminDeviceOperationTypes 12 }
xcmHrAdminDeviceFlushInOut      OBJECT IDENTIFIER
    ::= { xcmHrAdminDeviceOperationTypes 13 }
xcmHrAdminDeviceManage          OBJECT IDENTIFIER
    ::= { xcmHrAdminDeviceOperationTypes 14 }
xcmHrAdminDeviceRefresh         OBJECT IDENTIFIER
    ::= { xcmHrAdminDeviceOperationTypes 15 }
xcmHrAdminDeviceWarmUp          OBJECT IDENTIFIER
    ::= { xcmHrAdminDeviceOperationTypes 16 }
xcmHrAdminDeviceCoolDown        OBJECT IDENTIFIER
    ::= { xcmHrAdminDeviceOperationTypes 17 }
xcmHrAdminDeviceEnergySave      OBJECT IDENTIFIER
    ::= { xcmHrAdminDeviceOperationTypes 18 }
xcmHrAdminDeviceWakeUp          OBJECT IDENTIFIER
    ::= { xcmHrAdminDeviceOperationTypes 19 }
xcmHrAdminDevicePowerToReady    OBJECT IDENTIFIER
    ::= { xcmHrAdminDeviceOperationTypes 20 }
xcmHrAdminDevicePowerToStandby  OBJECT IDENTIFIER
    ::= { xcmHrAdminDeviceOperationTypes 21 }
xcmHrAdminDevicePowerToSleep    OBJECT IDENTIFIER
    ::= { xcmHrAdminDeviceOperationTypes 22 }

--
--          The Host Resources Extensions (HRX) TC
--
--          Textual Conventions

XcmHrDevCalendarDayOfWeek ::= TEXTUAL-CONVENTION
    STATUS      current
    DESCRIPTION
        "The day of week when the command specified in a conceptual
        row in the 'xcmHrDevCalendarTable' shall be invoked."
    SYNTAX      INTEGER {
        monday(1),
        tuesday(2),
        wednesday(3),
        thursday(4),
        friday(5),
        saturday(6),
        sunday(7),
        everyDay(8),                    -- monday through sunday
        businessOpenDay(9),             -- site specific
        businessClosedDay(10),          -- site specific
        businessHoliday(11)             -- site specific
    }


XcmHrDevCalendarTimeOfDay ::= TEXTUAL-CONVENTION
    STATUS      current
    DESCRIPTION
        "The time of day when the command specified in a conceptual
        row in the 'xcmHrDevCalendarTable' shall be invoked, specified
        as hours (0..23) multiplied by 100, added to minutes (0..59),
        added to a constant bias of 10000 (avoids an index value of zero
        in 'xcmHrDevCalendarTimeOfDay')."
    SYNTAX      INTEGER (10000..12359)

XcmHrDevDetailType ::= TEXTUAL-CONVENTION
    STATUS      current
    DESCRIPTION
        "The type of the device detail information specified
        in this conceptual row in the 'xcmHrDevDetailTable'.

        --  Device other/unknown details
      * 'other'
      * 'unknown'

        --  Device general info
      * 'deviceName'
        - device administrative name in directory (primary name)
        - see - 'xcmHrDevInfoName' in XCMI HRX MIB
        - see - DPA-1 9.4.1 'Printer-name'
        - see - DPA-1 9.5.1 'Server-name'
        - type - '...ValueOID' (directory in XCMI Comms Config TC)
        - (eg, 'xcmCONetwareNDS')
        - data - '...ValueString'
        - (eg, 'showstopper')
      * 'deviceAlias'
        - device administrative alias in directory (alternate name)
        - see - DPA-1 9.4.2 'Printer-name-aliases'
        - see - DPA-1 9.5.2 'Server-name-aliases'
        - type - '...ValueOID' (directory in XCMI Comms Config TC)
        - (eg, 'xcmCONetwareNDS')
        - data - '...ValueString'
        - (eg, 'LaserRat')
      * 'deviceType'
        - device type (read-write/read-create)
        - see - 'hrDeviceType' in IETF HR MIB
        - type - (OBJECT IDENTIFIER)
        - data - '...ValueOID'
        - (eg, 'hrDevicePrinter')
      * 'deviceDescription'
        - device description (read-write/read-create)
        - see - 'hrDeviceDescr' in IETF HR MIB
        - type - (XcmFixedLocaleDisplayString)
        - data - '...ValueString'
        - (eg, 'Xerox DC230 Model...')
      * 'deviceID'
        - device (product) ID (read-write/read-create)
        - see - 'ProductID' and 'hrDeviceID' in IETF HR MIB
        - type - (ProductID)


        - data - '...ValueOID'
        - (eg, 'xeroxDCS...')
      * 'deviceTree'
        - device tree prefix to name/alias in directory
        - type - '...ValueOID' (directory in XCMI Comms Config TC)
        - (eg, 'xcmCONetwareNDS')
        - data - '...ValueString'
        - (may also appear in 'deviceName')
      * 'deviceContext'
        - device context prefix to name/alias in directory
        - type - '...ValueOID' (directory in XCMI Comms Config TC)
        - (eg, 'xcmCONetwareNDS')
        - data - '...ValueString'
        - (may also appear in 'deviceName')
      * 'deviceManufacturer'
        - device manufacturer (or OEM) name
        - compare - 'hrDeviceDescr' in IETF HR MIB
        - type - (XcmFixedLocale...)
        - data - '...ValueString'
      * 'deviceModel'
        - device model (alphanumeric)
        - see - DPA-1 9.4.4 'Printer-model'
        - compare - 'hrDeviceDescr' in IETF HR MIB
        - type - (XcmFixedLocale...)
        - data - '...ValueString'
      * 'deviceSerialNumber'
        - device serial number
        - see - 'xcmHrDevInfoSerialNumber' in XCMI HRX MIB
        - type - (XcmFixedLocale...)
        - data - '...ValueString'
      * 'deviceVendor'
        - device vendor (to customer)
        - compare - 'hrDeviceDescr' in IETF HR MIB
        - type - (XcmFixedLocale...)
        - data - '...ValueString'
      * 'deviceVersion'
        - device version (alphanumeric)
        - compare - 'hrDeviceDescr' in IETF HR MIB
        - type - (XcmFixedLocale...)
        - data - '...ValueString'

        --  Device service info
      * 'deviceServiceByCustomer'
        - device serviced by customer (rather than vendor)
        - type - (TruthValue)
        - data - '...ValueInteger'
        - 'true' = serviced by customer
        - 'false' = serviced by vendor
      * 'deviceReplaceByCustomer'
        - device replaced by customer (rather than vendor)
        - type - (TruthValue)
        - data - '...ValueInteger'
        - 'true' = replaced by customer
        - 'false' = replaced by vendor


      * 'deviceServicePlanName'
        - device service plan name
        - type - (XcmFixedLocaleDisplayString)
        - data - '...ValueString'
        - (eg, 'Goldspot77')
      * deviceServicePlanPassword'
        - device service plan password (protected/encrypted)
        - type - (XcmFixedLocaleDisplayString)
        - data - '...ValueString'
        - (eg, 'EA123456')
      * 'deviceReplaceByWarranty'
        - device replaced by warranty (rather than at end-of-life)
        - type - (TruthValue)
        - data - '...ValueInteger'
        - 'true' = replaced by warranty (by some date or usage limit)
        - 'false' = replaced at end-of-life

        --  Device lifetime info
        --  (several usage counters may be defined for a single device)
        --  (several usage limits may be defined for a single counter)
        --  (usage counter and usage limit groups are defined as sharing
        --  the same value of 'xcmHrDevDetailIndex')
      * 'deviceLifetimeUsage'
        - device lifetime usage counter (may be multi-valued)
        - type - (Counter32)
        - data - '...ValueInteger'
        - (eg, power cycles and output lifetime counters)
      * 'deviceReorderLifetimeLimit'
        - device reorder at limit (may be multi-valued)
        - type - (Cardinal32)
        - data - '...ValueInteger'
        - positive integer = limit in 'xcmHrDevDetailUnit' units
        - zero = no limit specified
      * 'deviceWarningLifetimeLimit'
        - warn device user at usage limit (may be multi-valued)
        - type - (Cardinal32)
        - data - '...ValueInteger'
        - positive integer = limit in 'xcmHrDevDetailUnit' units
        - zero = no limit specified
      * 'deviceReplaceLifetimeLimit'
        - replace device at usage limit (may be multi-valued)
        - type - (Cardinal32)
        - data - '...ValueInteger'
        - positive integer = limit in 'xcmHrDevDetailUnit' units
        - zero = no limit specified
      * 'deviceMaximumLifetimeLimit'
        - stop device at usage limit (may be multi-valued)
        - type - (Cardinal32)
        - data - '...ValueInteger'
        - positive integer = limit in 'xcmHrDevDetailUnit' units
        - zero = no limit specified

        --  Device message to user time remaining
        --  (estimated dates when messages will be sent to the user)


        --  (estimated by the device, based on current rate of usage)
      * 'deviceDaysUntilReorderMsg'
        - days left until reorder msg (estimated from rate of usage)
        - type - days
        - data - '...ValueInteger'
      * 'deviceDaysUntilWarningMsg'
        - days left until warning msg (estimated from rate of usage)
        - type - days
        - data - '...ValueInteger'
      * 'deviceDaysUntilReplaceMsg'
        - days left until replace msg (estimated from rate of usage)
        - type - days
        - data - '...ValueInteger'
      * 'deviceDaysUntilMaximumMsg'
        - days left until stop msg (estimated from rate of usage)
        - type - days
        - data - '...ValueInteger'
      * 'deviceLifetimeMsgDisplay'
        - where to send lifetime msgs to user
        - type - local enum
        - data - '...ValueInteger'
        - '0' = none (no msg sent)
        - '1' = local device UI only
        - '2' = remote clients only
        - '3' = both (local and remote)

        --  Device message to user and reorder dates
        --  (fixed dates when messages will be sent to the user)
        --  (fixed by system administrator)
      * 'deviceReorderOnDate'
        - reorder device on fixed date (and send message to user)
        - type - (DateAndTime)
        - data - '...ValueString'
      * 'deviceWarningOnDate'
        - warn device user on fixed date
        - type - (DateAndTime)
        - data - '...ValueString'
      * 'deviceReplaceOnDate'
        - replace device on fixed date (and send message to user)
        - type - (DateAndTime)
        - data - '...ValueString'
      * 'deviceMaximumOnDate'
        - stop device on fixed date (and send message to user)
        - type - (DateAndTime)
        - data - '...ValueString'

        --  Device message to user triggers
        --  (actual days before an estimated limit date, when messages
        --  shall be sent to users)
        --  (while the 'triggers' are in terms of actual days, the
        --  determination of the [future] limit reached date is based
        --  on estimation by the device from current rate of usage)
      * 'deviceTriggerDaysForReorder'
        - days to reorder msg trigger (send before reorder limit)


        - type - (DateAndTime)
        - data - '...ValueString'
      * 'deviceTriggerDaysForWarning'
        - days to warning msg trigger (send before warning limit)
        - type - (DateAndTime)
        - data - '...ValueString'
      * 'deviceTriggerDaysForReplace'
        - days to replace msg trigger (send before replace limit)
        - type - (DateAndTime)
        - data - '...ValueString'
      * 'deviceTriggerDaysForMaximum'
        - days to stop msg trigger (send before stop limit)
        - type - (DateAndTime)
        - data - '...ValueString'

        --  Device message to user dates actually sent
        --  (log of dates when messages were actually sent to user,
        --  based on estimates, actual limits, actual dates, etc)
      * 'deviceReorderMsgSentDate'
        - date of reorder msg to user (may be multi-valued)
        - type - (DateAndTime)
        - data - '...ValueString'
      * deviceWarningMsgSentDate'
        - date of warning msg to user (may be multi-valued)
        - type - (DateAndTime)
        - data - '...ValueString'
      * 'deviceReplaceMsgSentDate'
        - date of replace msg to user (may be multi-valued)
        - type - (DateAndTime)
        - data - '...ValueString'
      * 'deviceMaximumMsgSentDate'
        - date of maximum msg to user (may be multi-valued)
        - type - (DateAndTime)
        - data - '...ValueString'

        --  Device reorder and replace actual dates
        --  (log of dates when reorder and replacement were actually
        --  done for this device)
      * 'deviceReorderToVendorDate'
        - date reorder to vendor sent (may be multi-valued)
        - type - (DateAndTime)
        - data - '...ValueString'
      * 'deviceReorderConfirmDate'
        - date reorder confirm received (may be multi-valued)
        - type - (DateAndTime)
        - data - '...ValueString'
      * 'deviceReplaceDate'
        - date of replacement (may be multi-valued)
        - type - (DateAndTime)
        - data - '...ValueString'
      * 'deviceReplaceSystemUsage'
        - system usage at date of replacement (may be multi-valued)
        - type - some usage counter
        - (eg, 'total marked images')


        - date - '...ValueInteger'

        --  Device help info (contact info)
      * 'deviceHelpName'
        - device help person name and role
        - type - '...ValueOID' (directory in XCMI Comms Config TC)
        - (eg, 'xcmCONetwareBindery')
        - data - '...ValueString'
        - (eg, 'Joe Hampton')
        - role - '...ValueInteger' (XcmSecUserRole in XCMI Security TC)
        - (eg, 'systemOperator')
      * 'deviceHelpAddress'
        - device help person address and role
        - type - '...ValueOID' (address type in XCMI Comms Config TC)
        - (eg, 'xcmCOOsiwanFax')
        - data - '...ValueString'
        - (eg, '1-800-232-7979')
        - role - '...ValueInteger' (XcmSecUserRole in XCMI Security TC)
        - (eg, 'systemOperator')
      * 'deviceHelpDescription'
        - device help person description
        - type - (XcmFixedLocaleDisplayString)
        - data - '...ValueString'
        - (eg, 'has keys to supplies')
      * 'deviceHelpLocation'
        - device help person physical location
        - see - DPA-1 9.4.3 'Printer-locations'
        - type - (XcmFixedLocaleDisplayString)
        - data - '...ValueString'
        - (eg, '3rd floor lobby')

        --  Device supported and ready info
        --  (from ISO 10175 DPA-1 Section 9.4 'Printer Object')
        --  (see 9.4.74 'Common Printer and Server object attributes')
      * 'deviceTranslatorSupport'
        - see - DPA-1 9.4.74.5 'Translators-supported'
        - type - (XcmFixedLocaleDisplayString)
        - data - '...ValueString'
      * 'deviceTranslatorReady'
        - see - DPA-1 9.4.74.6 'Translators-ready'
        - type - (XcmFixedLocaleDisplayString)
        - data - '...ValueString'
      * 'deviceInitialValueJobSupport'
        - see - DPA-1 9.4.74.13 'Initial-value-jobs-supported'
        - type - (XcmFixedLocaleDisplayString)
        - data - '...ValueString'
      * 'deviceInitialValueDocSupport'
        - see - DPA-1 9.4.74.14 'Initial-value-documents-supported'
        - type - (XcmFixedLocaleDisplayString)
        - data - '...ValueString'
      * 'deviceMultipleDocSupport'
        - see - DPA-1 9.4.74.3 'Multiple-documents-supported'
        - type - (TruthValue)
        - data - '...ValueInteger'


      * 'deviceCancelDocSupport'
        - see - DPA-1 9.4.74.4 'Cancel-individual-documents-supported'
        - type - (TruthValue)
        - data - '...ValueInteger'
      * 'deviceForeignJobsVisible'
        - see - DPA-1 9.4.74.15 'Are-foreign-jobs-visible'
        - type - (TruthValue)
        - data - '...ValueInteger'
      * 'deviceInitialValueJobDefault'
        - see - DPA-1 9.4.12 'Printer-initial-value-job'
        - type - (XcmFixedLocaleDisplayString)
        - data - '...ValueString'
      * 'deviceInitialValueDocDefault'
        - see - DPA-1 9.4.13 'Printer-initial-value-document'
        - type - (XcmFixedLocaleDisplayString)
        - data - '...ValueString'
      * 'deviceInputMaxSpeedTrafficUnit'
        - traffic unit of numerator of device input max speed
        - see - DPA-1 9.4.7 'Maximum-printer-speed'
        - type - (XcmHrDevTrafficUnit)
        - data - '...ValueInteger'
      * 'deviceInputMaxSpeedTimeUnit'
        - time unit of divisor of device input max speed
        - see - DPA-1 9.4.7 'Maximum-printer-speed'
        - type - (XcmHrDevPowerTimeUnit)
        - data - '...ValueInteger'
      * 'deviceInputMaxSpeed'
        - device input max speed
        - see - DPA-1 9.4.7 'Maximum-printer-speed'
        - type - (Cardinal32)
        - data - '...ValueInteger'
      * 'deviceOutputMaxSpeedTrafficUnit'
        - traffic unit of numerator of device output max speed
        - see - DPA-1 9.4.7 'Maximum-printer-speed'
        - type - (XcmHrDevTrafficUnit)
        - data - '...ValueInteger'
      * 'deviceOutputMaxSpeedTimeUnit'
        - time unit of divisor of device output max speed
        - see - DPA-1 9.4.7 'Maximum-printer-speed'
        - type - (XcmHrDevPowerTimeUnit)
        - data - '...ValueInteger'
      * 'deviceOutputMaxSpeed'
        - device output max speed
        - see - DPA-1 9.4.7 'Maximum-printer-speed'
        - type - (Cardinal32)
        - data - '...ValueInteger'
      * 'deviceFeedResolutionSupport'
        - see - DPA-1 9.4.8 'Printer-resolutions-supported'
        - type - DPI (dots per inch)
        - data - '...ValueInteger'
      * 'deviceXFeedResolutionSupport'
        - see - DPA-1 9.4.8 'Printer-resolutions-supported'
        - type - DPI (dots per inch)
        - data - '...ValueInteger'


      * 'deviceSchedulerSupport'
        - see - DPA-1 9.4.63 'Schedulers-supported'
        - type - (XcmFixedLocaleDisplayString)
        - data - '...ValueString'
      * 'deviceSchedulerReady'
        - see - DPA-1 9.4.64 'Scheduler-ready'
        - type - (XcmFixedLocaleDisplayString)
        - data - '...ValueString'

        --  Device supported and ready device name info (list)
      * 'devicePhysicalNameSupport'
        - see - DPA-1 9.4.10 'Printer-associated-printers'
        - see - DPA-1 9.5.6 'Physical-printers-supported' (servers)
        - type - (XcmFixedLocaleDisplayString)
        - data - '...ValueString'
      * 'devicePhysicalNameReady'
        - see - DPA-1 9.4.11 'Printers-ready'
        - see - DPA-1 9.5.7 'Physical-printers-ready' (servers)
        - type - (XcmFixedLocaleDisplayString)
        - data - '...ValueString'
      * 'deviceLogicalNameSupport'
        - see - DPA-1 9.4.10 'Printer-associated-printers'
        - see - DPA-1 9.5.8 'Logical-printers-supported' (servers)
        - type - (XcmFixedLocaleDisplayString)
        - data - '...ValueString'
      * 'deviceLogicalNameReady'
        - see - DPA-1 9.4.11 'Printers-ready'
        - see - DPA-1 9.5.9 'Logical-printers-ready' (servers)
        - type - (XcmFixedLocaleDisplayString)
        - data - '...ValueString'

        --  Device supported and ready device index info (list)
      * 'devicePhysicalIndexSupport'
        - see - DPA-1 9.4.10 'Printer-associated-printers'
        - see - DPA-1 9.5.6 'Physical-printers-supported' (servers)
        - type - 'hrDeviceIndex'
        - data - '...ValueInteger'
      * 'devicePhysicalIndexReady'
        - see - DPA-1 9.4.11 'Printers-ready'
        - see - DPA-1 9.5.7 'Physical-printers-ready' (servers)
        - type - 'hrDeviceIndex'
        - data - '...ValueInteger'
      * 'deviceLogicalIndexSupport'
        - see - DPA-1 9.4.10 'Printer-associated-printers'
        - see - DPA-1 9.5.8 'Logical-printers-supported' (servers)
        - type - 'hrDeviceIndex'
        - data - '...ValueInteger'
      * 'deviceLogicalIndexReady'
        - see - DPA-1 9.4.11 'Printers-ready'
        - see - DPA-1 9.5.9 'Logical-printers-ready' (servers)
        - type - 'hrDeviceIndex'
        - data - '...ValueInteger'

        --  Device supported and ready font/resource index info (list)


      * 'deviceFontIndexSupport'
        - see - DPA-1 9.4.19 'Fonts-supported'
        - type - 'xcmFontIndex' in XCMI Resources MIB
        - data - '...ValueInteger'
      * 'deviceFontIndexReady'
        - see - DPA-1 9.4.20 'Fonts-ready'
        - type - 'xcmFontIndex' in XCMI Resources MIB
        - data - '...ValueInteger'
      * 'deviceResourceIndexSupport'
        - see - DPA-1 9.4.21 'Resources-supported'
        - type - 'xcmRsrcIndex' in XCMI Resources MIB
        - data - '...ValueInteger'
      * 'deviceResourceIndexReady'
        - see - DPA-1 9.4.22 'Resources-ready'
        - type - 'xcmRsrcIndex' in XCMI Resources MIB
        - data - '...ValueInteger'

        --  Device power management
      * 'devicePowerModeName'
        - device power mode administrative name (locale dependent)
        - type - (XcmFixedLocaleDisplayString)
        - data - '...ValueString'
      * 'devicePowerModeType'
        - device power mode type (locale independent)
        - type - (XcmHrDevPowerModeType)
        - data - '...ValueInteger'
      * 'devicePowerModeDescription'
        - device power mode description (locale dependent)
        - type - (XcmFixedLocaleDisplayString)
        - data - '...ValueString'
      * 'devicePowerModeSupport'
        - device power mode support (may be used to disable a mode)
        - type - (PresentOnOff)
        - data - '...ValueInteger'
      * 'devicePowerTimeUnit'
        - device power mode transition time unit (defaults to seconds)
        - type - (XcmHrDevPowerTimeUnit)
        - data - '...ValueString'
      * 'devicePowerWarmerSupport'
        - device power mode to warmer mode transition support
        - type - (PresentOnOff)
        - data - '...ValueInteger'
      * 'devicePowerCoolerSupport'
        - device power mode to cooler mode transition support
        - type - (PresentOnOff)
        - data - '...ValueInteger'
      * 'devicePowerWarmerDelay'
        - device power mode to warmer mode transition delay
        - (delay after trigger event until transition begins)
        - type - (XcmHrDevPowerTimeUnit)
        - data - '...ValueInteger'
      * 'devicePowerWarmerDuration'
        - device power mode to warmer mode transition duration
        - (duration after transition begins until transition completes)


        - type - (XcmHrDevPowerTimeUnit)
        - data - '...ValueInteger'
      * 'devicePowerCoolerDelay'
        - device power mode to cooler mode transition delay
        - (delay after trigger event until transition begins)
        - type - (XcmHrDevPowerTimeUnit)
        - data - '...ValueInteger'
      * 'devicePowerCoolerDuration'
        - device power mode to cooler mode transition duration
        - (duration after transition begins until transition completes)
        - type - (XcmHrDevPowerTimeUnit)
        - data - '...ValueInteger'
      * 'devicePowerWarmerTrigger'
        - device warmer mode trigger description
        - type - (XcmFixedLocaleDisplayString)
        - data - '...ValueString'
      * 'devicePowerCoolerTrigger'
        - device cooler mode trigger description
        - type - (XcmFixedLocaleDisplayString)
        - data - '...ValueString'
      * 'deviceNextWarmerModeIndex'
        - device next warmer mode pointer (in device details)
        - type - 'xcmHrDevDetailIndex'
        - data - '...ValueInteger'
      * 'deviceNextCoolerModeIndex'
        - device next cooler mode pointer (in device details)
        - type - 'xcmHrDevDetailIndex'
        - data - '...ValueInteger'

        --  Device 'hrDeviceProcessor' details
      * 'deviceProcessorFrwID'
        - device firmware ID (read-write/read-create)
        - type - 'hrProcessorFrwID'
        - data - '...ValueOID'

        --  Device 'hrDeviceNetwork' details
      * 'deviceNetworkIfIndex'
        - device interface index (read-write/read-create)
        - type - 'hrNetworkIfIndex'
        - data - '...ValueInteger'

        --  Device 'hrDeviceDiskStorage' details
      * 'deviceDiskStorageAccess'
        - device disk access (read-write/read-create)
        - type - 'hrDiskStorageAccess'
        - data - '...ValueInteger'
      * 'deviceDiskStorageMedia'
        - device disk media (read-write/read-create)
        - type - 'hrDiskStorageMedia'
        - data - '...ValueInteger'
      * 'deviceDiskStorageRemovable'
        - device removable (read-write/read-create)
        - type - 'hrDiskStorageRemoveble' ('removable' - Oxford Concise)
        - data - '...ValueInteger'


      * 'deviceDiskStorageCapacity'
        - device capacity (read-write/read-create)
        - type - 'hrDiskStorageCapacity'
        - data - '...ValueInteger'

        --  Device guest/alien job and log full policies
      * 'deviceGuestJobPolicy'
        - device policy for jobs with 'guest' (empty) user/account
        - see - 'xcmSecServiceGuestJobPolicy' in XCMI Security MIB
        - type - 'XcmSecGuestJobPolicy'
        - data - '...ValueInteger'
      * 'deviceAlienJobPolicy'
        - device policy for jobs with 'alien' (invalid) user/account
        - see - 'xcmSecServiceAlienJobPolicy' in XCMI Security MIB
        - type - 'XcmSecGuestJobPolicy'
        - data - '...ValueInteger'
      * 'deviceEventLogFullPolicy'
        - device policy for handling event log full conditions
        - see - 'xcmSecServiceEventLogFullPolicy' in XCMI Security MIB
        - see - DPA-1 9.1.6.8 'Notification-profile' (events)
        - see - DPA-1 9.4 'Printer Object attributes' (generic)
        - type - 'XcmGenLogFullPolicy'
        - data - '...ValueInteger'
      * 'deviceJobLogFullPolicy'
        - device policy for handling job log full conditions
        - see - 'xcmSecServiceJobLogFullPolicy' in XCMI Security MIB
        - see - DPA-1 9.1.6.9 'Logging-profile' (jobs)
        - see - DPA-1 9.4 'Printer Object attributes' (generic)
        - type - 'XcmGenLogFullPolicy'
        - data - '...ValueInteger'
      * 'deviceRequestLogFullPolicy'
        - device policy for handling request log full conditions
        - see - 'xcmSecServiceRequestLogFullPolicy' in XCMI Security MIB
        - type - 'XcmGenLogFullPolicy'
        - data - '...ValueInteger'

        Usage:  Conforming management stations and management agents
        shall implement the above semantics for device detail types."
    REFERENCE
        "See:   'xcmHrDevDetailUnitClass' and
                'xcmHrDevDetailUnit' for syntax of device detail."
    SYNTAX      INTEGER {
        --  Device other/unknown details
        other(1),
        unknown(2),
        --  Device general info
        deviceName(3),
        deviceAlias(4),
        deviceType(5),
        deviceDescription(6),
        deviceID(7),
        deviceTree(8),
        deviceContext(9),
        deviceManufacturer(10),


        deviceModel(11),
        deviceSerialNumber(12),
        deviceVendor(13),
        deviceVersion(14),
        --  Device service info
        deviceServiceByCustomer(15),
        deviceReplaceByCustomer(16),
        deviceServicePlanName(17),
        deviceServicePlanPassword(18),
        deviceReplaceByWarranty(19),
        --  Device lifetime info
        deviceLifetimeUsage(20),
        deviceReorderLifetimeLimit(21),
        deviceWarningLifetimeLimit(22),
        deviceReplaceLifetimeLimit(23),
        deviceMaximumLifetimeLimit(24),
        --  Device message to user time remaining
        deviceDaysUntilReorderMsg(25),
        deviceDaysUntilWarningMsg(26),
        deviceDaysUntilReplaceMsg(27),
        deviceDaysUntilMaximumMsg(28),
        deviceLifetimeMsgDisplay(29),
        --  Device message to user and reorder dates
        deviceReorderOnDate(31),
        deviceWarningOnDate(32),
        deviceReplaceOnDate(33),
        deviceMaximumOnDate(34),
        --  Device message to user triggers
        deviceTriggerDaysForReorder(41),
        deviceTriggerDaysForWarning(42),
        deviceTriggerDaysForReplace(43),
        deviceTriggerDaysForMaximum(44),
        --  Device message to user dates actually sent
        deviceReorderMsgSentDate(51),
        deviceWarningMsgSentDate(52),
        deviceReplaceMsgSentDate(53),
        deviceMaximumMsgSentDate(54),
        --  Device reorder and replace actual dates
        deviceReorderToVendorDate(55),
        deviceReorderConfirmDate(56),
        deviceReplaceDate(57),
        deviceReplaceSystemUsage(58),
        --  Device help info (contact info)
        deviceHelpName(60),
        deviceHelpAddress(61),
        deviceHelpDescription(62),
        deviceHelpLocation(63),
        --  Device supported and ready info
        deviceTranslatorSupport(71),
        deviceTranslatorReady(72),
        deviceInitialValueJobSupport(73),
        deviceInitialValueDocSupport(74),
        deviceMultipleDocSupport(75),
        deviceCancelDocSupport(76),


        deviceForeignJobsVisible(77),
        deviceInitialValueJobDefault(78),
        deviceInitialValueDocDefault(79),
        deviceInputMaxSpeedTrafficUnit(80),
        deviceInputMaxSpeedTimeUnit(81),
        deviceInputMaxSpeed(82),
        deviceOutputMaxSpeedTrafficUnit(83),
        deviceOutputMaxSpeedTimeUnit(84),
        deviceOutputMaxSpeed(85),
        deviceFeedResolutionSupport(86),
        deviceXFeedResolutionSupport(87),
        deviceSchedulerSupport(88),
        deviceSchedulerReady(89),
        --  Device supported and ready device name info (list)
        devicePhysicalNameSupport(90),
        devicePhysicalNameReady(91),
        deviceLogicalNameSupport(92),
        deviceLogicalNameReady(93),
        --  Device supported and ready device index info (list)
        devicePhysicalIndexSupport(94),
        devicePhysicalIndexReady(95),
        deviceLogicalIndexSupport(96),
        deviceLogicalIndexReady(97),
        --  Device supported and ready font/resource index info (list)
        deviceFontIndexSupport(100),
        deviceFontIndexReady(101),
        deviceResourceIndexSupport(102),
        deviceResourceIndexReady(103),
        --  Device power management
        devicePowerModeName(110),
        devicePowerModeType(111),
        devicePowerModeDescription(112),
        devicePowerModeSupport(113),
        devicePowerTimeUnit(114),
        devicePowerWarmerSupport(115),
        devicePowerCoolerSupport(116),
        devicePowerWarmerDelay(117),
        devicePowerWarmerDuration(118),
        devicePowerCoolerDelay(119),
        devicePowerCoolerDuration(120),
        devicePowerWarmerTrigger(121),
        devicePowerCoolerTrigger(122),
        deviceNextWarmerModeIndex(123),
        deviceNextCoolerModeIndex(124),
        --  Device 'hrDeviceProcessor' details
        deviceProcessorFrwID(130),
        --  Device 'hrDeviceNetwork' details
        deviceNetworkIfIndex(140),
        --  Device 'hrDeviceDiskStorage' details
        deviceDiskStorageAccess(160),
        deviceDiskStorageMedia(161),
        deviceDiskStorageRemovable(162),
        deviceDiskStorageCapacity(163),
        --  Device guest/alien job and log full policies


        deviceGuestJobPolicy(200),
        deviceAlienJobPolicy(201),
        deviceEventLogFullPolicy(202),
        deviceJobLogFullPolicy(203),
        deviceRequestLogFullPolicy(204)
    }

XcmHrDevDetailUnitClass ::= TEXTUAL-CONVENTION
    STATUS      current
    DESCRIPTION
        "The value unit class of the device detail information specified
        in this conceptual row in the 'xcmHrDevDetailTable'.

        Usage:  Used to select a textual convention for specifying the
        units of this device detail value."
    SYNTAX      INTEGER {
        other(1),
        unknown(2),
        classGenOptionValueSyntax(3),   -- XcmGenOptionValueSyntax
        classDateAndTime(4),            -- DateAndTime (from SNMPv2-TC)
        classHrDevCalendarDayOfWeek(5), -- XcmHrDevCalendarDayOfWeek
        classHrDevCalendarTimeOfDay(6), -- XcmHrDevCalendarTimeOfDay
        classHrDevMgmtCommandRequest(7),-- XcmHrDevMgmtCommandRequest
        classHrDevPowerTimeUnit(8),     -- XcmHrDevPowerTimeUnit
        classHrDevTrafficUnit(9),       -- XcmHrDevTrafficUnit
        classRowPersistence(10)         -- XcmGenRowPersistence
    }

XcmHrDevInfoRealization ::= TEXTUAL-CONVENTION
    STATUS      current
    DESCRIPTION
        "An extended device type (or device 'realization'),
        used by system administrators and end users of this device.

        Usage:  The use of either 'other' or 'unknown' is uninformative
        and should be avoided by conforming implementations.

      * 'physical' - 'real' device installed on this managed system;
      * 'logical' - 'virtual' device configured on this managed system;
      * 'logicalAndPhysical' - 'combined' device (from ISO DPA ??)."
    REFERENCE
        "See:   'hrDeviceType' in the basic Device Group of the
        IETF Host Resources MIB (RFC 1514).
        See:    Section 9.4 'Printer Object attributes' of ISO DPA
        (Document Printing Application) ISO/IEC 10175 (Final Text, March
        1996) for a discussion of 'printer realizations' of 'physical',
        'logical', and 'logical-and-physical' types (the latter unique
        to DPA)."
    SYNTAX      INTEGER {
        other(1),                       -- other device       
        unknown(2),                     -- unknown device     
        physical(11),                   -- 'real' device
        logical(12),                    -- 'virtual' device
        logicalAndPhysical(13)          -- 'combined' device


    }

XcmHrDevInfoStatus ::= TEXTUAL-CONVENTION
    STATUS      current
    DESCRIPTION
        "The current operational state of the device
        described by this row of the table.  A value
        'unknown(1)' indicates that the current state of the
        device is unknown.  'running(2)' indicates that the
        device is up and running and that no unusual error
        conditions are known.  The 'warning(3)' state
        indicates that agent has been informed of an
        unusual error condition by the operational software
        (eg, a disk device driver) but that the device is
        still 'operational'.  An example would be a high
        number of soft errors on a disk.  A value of
        'testing(4)', indicates that the device is not
        available for use because it is in the testing
        state.  The state of 'down(5)' is used only when the
        agent has been informed that the device is not
        available for any use.

        Usage:  Conforming implementations shall NOT 'bubble up' status
        from 'physical' devices to associated 'logical' devices.  All
        devices shall ALWAYS report their own status ONLY.

        Usage:  Devices in the 'down' state should NOT be accepting new
        work (or still processing old work).  Devices in the 'running'
        state should be prepared to accept new work.

        Usage:  The use of the state 'unknown' is uninformative
        and should be avoided by conforming implementations.

        Usage:  This is a textual convention representation of the
        'hrDeviceStatus' enumeration in the IETF Host Resources MIB
        (RFC 1514), rewritten from SMIv1 style (RFCs 1155 and 1212) into
        SMIv2 style (RFCs 1442/1902, 1443/1903, and 1444/1904)."
    REFERENCE
        "See:   'hrDeviceStatus' in the basic Device Group of the
        IETF Host Resources MIB (RFC 1514).
        See:    'xcmHrDevInfoXStatus', 'xcmHrDevInfoConditions', and
        'xcmHrDevInfoXConditions' in the Host Resources Extensions MIB."
    SYNTAX      INTEGER {
        unknown(1),                     -- indeterminate      
        running(2),                     -- normally operational, started
        warning(3),                     -- operational, but alert posted
        testing(4),                     -- not operational, testing
        down(5)                         -- not operational, shutdown
    }


XcmHrDevInfoXStatus ::= TEXTUAL-CONVENTION
    STATUS      current
    DESCRIPTION
        "An extended device status, used by system administrators
        and end users of this device (here, read 'state' for 'status').

        Usage:  Conforming implementations shall NOT 'bubble up' status
        from 'physical' devices to associated 'logical' devices.  All
        devices shall ALWAYS report their own status ONLY.

        Usage:  Exactly one enumeration of extended device status
        shall be defined, with ranges for each basic device type (eg,
        'hrDevicePrinter').  The legal range for extended device status
        for a given device type (either defined by RFC 1514 or by this
        MIB) is found by multiplying the final arc of the the device
        type OID by 100 - the result is the device specific range base -
        the end of the device specific range is 99 larger.  These device
        specific extended device status values shall be reissued
        periodically in the 'XcmHrDevInfoXStatus' textual convention."
    REFERENCE
        "See:   Section 9.4.9 'Printer-state' of ISO DPA
        (Document Printing Application) ISO/IEC 10175 (Final Text,
        18 May 1995) for a discussion of the printer states used here.
        Note that the DPA state 'connecting-to-printer' has no meaning
        in the context of a 'physical' printer device, but only in the
        context of an intermediate DP-Server presenting a 'logical'
        printer device.
        See:    'hrPrinterStatus' and 'hrPrinterDetectedErrorState' in
        the IETF Host Resources MIB (RFC 1514) for related discussion.

        See:    'hrDeviceStatus' in the basic Device Group of the
        IETF Host Resources MIB (RFC 1514).
        See:    'xcmHrDevInfoConditions' and 'xcmHrDevInfoXConditions'
        in the Host Resources Extensions MIB."
    SYNTAX      INTEGER {
        --  Common extended device status
        commonNone(0),
        commonOther(1),
        commonUnknown(2),
        commonLast(99),

        --  'hrDeviceOther'
        otherNone(100),

        --  'hrDeviceUnknown'
        unknownNone(200),

        --  'hrDeviceProcessor'
        processorNone(300),

        --  'hrDeviceNetwork'
        networkNone(400),

        --  'hrDevicePrinter'


        --  See:    Section 9.4.9 'Printer-state' of ISO/IEC 10175
        --          (was on page 185 in earlier text, May 1995)
        --  See:    'id-val-printer-state-...' in Annex A of ISO/IEC
        --          10175 (was on page 307 in earlier text, May 1995)
        --  If 'dpaPrinterStateFinalArc' is truncated from an OID
        --  'id-val-printer-state-...' in Annex A of ISO/IEC 10175
        --  and 'xcmiPrinterStatus' is the corresponding enum value of
        --  'printer...' in 'XcmHrDevInfoXStatus' (below),
        --  then:
        --      xcmiPrinterStatus = (dpaPrinterStateFinalArc + 502)
        printerNone(500),               -- XCMI extension to ISO DPA
        printerOther(501),              -- XCMI extension to ISO DPA
        printerUnknown(502),            -- unknown or indeterminate
        printerIdle(503),               -- ready to accept jobs
        printerPrinting(504),           -- currently printing a job
        printerNeedsAttention(505),     -- needs general human attention
        printerPaused(506),             -- paused by user or operator
        printerShutdown(507),           -- taken out of service
        printerJobStartWait(508),       -- see ISO DPA 'job-start-wait'
        printerJobEndWait(509),         -- see ISO DPA 'job-end-wait'
        printerNeedsKeyOperator(510),   -- needs toner, developer, etc
        printerJobPasswordWait(511),    -- see ISO DPA 'job-password'
        printerTimedOut(512),           -- ISO DPA Servers only
        printerConnectingToPrinter(513),-- ISO DPA Servers only

        --  'hrDeviceDiskStorage'
        diskStorageNone(600),

        --  'hrDeviceVideo'
        videoNone(1000),

        --  'hrDeviceAudio'
        audioNone(1100),

        --  'hrDeviceCoprocessor'
        coprocessorNone(1200),

        --  'hrDeviceKeyboard'
        keyboardNone(1300),

        --  'hrDeviceModem'
        modemNone(1400),

        --  'hrDeviceParallelPort'
        parallelPortNone(1500),

        --  'hrDevicePointing'
        pointingNone(1600),

        --  'hrDeviceSerialPort'
        serialPortNone(1700),

        --  'hrDeviceTape'
        tapeNone(1800),


        --  'hrDeviceClock'
        clockNone(1900),

        --  'hrDeviceVolatileMemory'
        volatileMemoryNone(2000),

        --  'hrDeviceNonVolatileMemory'
        nonVolatileMemoryNone(2100),

        --  'xcmHrDeviceHostSystem'
        hostSystemNone(10100),

        --  'xcmHrDeviceScanner'
        scannerNone(10200),

        --  'xcmHrDeviceCopier'
        copierNone(10300),

        --  'xcmHrDeviceFax'
        faxNone(10400),

        --  'xcmHrDeviceMailbox'
        mailboxNone(10500),

        reserved(40000)                 -- placeholder
    }

XcmHrDevInfoConditions ::= TEXTUAL-CONVENTION
    STATUS      current
    DESCRIPTION
        "A relatively generic description of the current 'conditions'
        of this device.

              1 : startupInProgress
              2 : resetWarningInProgresss                     (optional)
              4 : testInProgress
              8 : shutdownInProgress                          (optional)
             16 : quiesceInProgress                           (optional)
             32 : resetCountersInProgress                     (optional)
             64 : resetWarmInProgress
            128 : resetColdInProgress
            256 : resetFactoryInProgress
            512 : flushInputInProgress
           1024 : flushOutputInProgress
           2048 : flushInOutInProgress
           4096 : manageInProgress                            (optional)

        The above basic 'conditions' record the original intent of the
        current command, when it results in delayed state transitions
        before arriving at the 'target' state.  They augment the state
        information available from 'hrDeviceStatus'.

           8192 : warmUpDelayInProgress                       (optional)


          16384 : warmUpCycleInProgress                       (optional)
          32768 : readyMode             -- warm up done       (optional)
          65536 : coolDownDelayInProgress                     (optional)
         131072 : coolDownCycleInProgress                     (optional)
         262144 : standbyMode           -- cool down done     (optional)
         524288 : energySaveDelayInProgress                   (optional)
        1048576 : energySaveCycleInProgress                   (optional)
        2097152 : sleepMode             -- energy save done   (optional)
        4194304 : wakeUpDelayInProgress                       (optional)
        8388608 : wakeUpCycleInProgress                       (optional)
       16777216 : powerToReadyInProgress                      (optional)
       33554432 : powerToStandbyInProgress                    (optional)
       67108864 : powerToSleepInProgress                      (optional)

        The above optional 'conditions' record the progress of device
        'warm up', 'cool down', 'energy save', and 'wake up' power mgmt
        cycles and also define the device 'readyMode', 'standbyMode',
        and 'sleepMode' qualifiers to the generic 'hrDeviceStatus' of
        'running(2)', 'warning(3)', or 'testing(4)' (but NOT 'down(5)').
        See the power management cycle feature support and feature time
        objects in the Device Power Group of the Host Resources Ext MIB.

        Usage:  It is desirable that the implementor report 'conditions'
        of all devices corresponding to conceptual rows in the
        'hrDeviceTable' as accurately as feasible.  'Conditions' occur
        within or across 'states' in a finite state machine (FSM)
        implementation of a device.  They represent both short term and
        long term conditions.

        Usage:  A device with 'hrDeviceStatus' of 'running(2)' might
        have 'xcmHrDevInfoConditions' of 'quiesceInProgress', indicating
        that the device will soon transition to 'hrDeviceStatus' of
        'down(5)'.

        Usage:  A multi-bit example of 'xcmHrDevInfoConditions' is
        'quiesceInProgress' concurrently with 'standbyMode', ie, the
        device has previously 'cooled down' and will soon transition
        from 'hrDeviceStatus' of 'running(2)' to 'down(5)'."
    REFERENCE
        "See:   'hrDeviceStatus' in the basic Device Group of the
        IETF Host Resources MIB (RFC 1514).
        See:    'xcmHrDevInfoXStatus' and 'xcmHrDevInfoXConditions'
        in the Host Resources Extensions MIB."
    SYNTAX      INTEGER (0..2147483647)  -- biggest int = 2**31-1

XcmHrDevInfoXConditions ::= TEXTUAL-CONVENTION
    STATUS      current
    DESCRIPTION
        "A device specific description of the extended 'conditions'
        of this device.

        Usage:  For FUTURE expansion.

        Usage:  Exactly one bit mask of extended device conditions shall


        be defined for each basic device type (eg, 'hrDevicePrinter').
        These device specific extended device conditions values shall be
        reissued periodically in the 'XcmHrDevInfoXConditions' textual
        convention.  These device specific extended device conditions
        are mutually exclusive and 'overloaded' in the single reporting
        object 'xcmHrDevInfoXConditions'."
    REFERENCE
        "See:   'hrDeviceStatus' in the basic Device Group of the
        IETF Host Resources MIB (RFC 1514).
        See:    'xcmHrDevInfoXStatus' and 'xcmHrDevInfoConditions'
        in the Host Resources Extensions MIB."
    SYNTAX      INTEGER (0..2147483647)  -- biggest int = 2**31-1

XcmHrDevMgmtCommandRequest ::= TEXTUAL-CONVENTION
    STATUS      current
    DESCRIPTION
        "A write of this type by an (authorized) management station
        invokes a command for this device.
        A read of this type always returns the command currently in
        progress or last completed.
        It is mandatory that a conforming management agent ensure that
        the contents of this object remain 'in bounds' - an undefined
        value shall be replaced by 'none' - ie, although rejected with
        error in the SetResponse PDU, this object shall NOT contain any
        such undefined value.  At system initialization, this object
        shall contain 'none'.

      * 'none' - NO action(s) shall be taken, except to ALWAYS clear
        '...CommandData' and set '...CommandStatus' to 'noError'.
      * 'test' or 'manage' - the associated '...CommandData' object
        should/shall be specified in the same SetRequest PDU.
      * all other commands - the associated '...CommandData' object
        MAY be specified in the same SetRequest PDU.
      * 'startup', 'resetWarm', 'resetCold', or 'resetFactory' - the
        final state shall be 'running' (after cycle completes) - the
        sequence of states should be 'down' -> 'testing' -> 'running' -
        the final power mode shall be 'ready'.
      * 'startup' - this device shall transition from the 'down' state
        to the 'running' state and 'ready' power mode.
      * 'resetWarning' - this device shall transition from the 'warning'
        state to the 'running' state (because a management station has
        acknowledged the management agent's previous warning).
      * 'test' - this device shall transition immediately (ie, without
        attempting graceful quiesce) to the 'testing' state; it is a
        local matter (ie, device specific) how this command is
        processed; however, '...CommandData' should be specified.
      * 'shutdown' - this device shall transition immediately (ie,
        without attempting graceful quiesce) to the 'down' state and
        'off' power mode.
      * 'quiesce' - this device MAY transition gracefully to the 'down'
        state, or it MAY choose to treat a 'quiesce' as 'shutdown'.
      * 'resetCounters' - all device counters shall be reset to zero and
        the device shall remain in the same state and power mode.
      * 'resetWarm' - a device 'warm restart' shall be performed (ie,


        without a power cycle reset).
      * 'resetCold' - a device 'cold restart' shall be performed (ie,
        with a power cycle reset).
      * 'resetFactory' - all factory defaults shall be restored, and a
        device 'cold restart' shall be performed (ie, with a power cycle
        reset).
      * 'flushInput' - all device input (in progress or internally
        queued) shall be gracefully flushed.
      * 'flushOutput' - all device output (in progress or internally
        queued) shall be gracefully flushed.
      * 'flushInOut' - all device input and output output (in progress
        or internally queued) shall be gracefully flushed.
      * 'manage' - it is a local matter (ie, device specific) how this
        command is processed; however, '...CommandData' shall be
        specified.
      * 'refresh' - the device shall promptly read all of its manageable
        configuration parameters, but shall NOT perform a reset.
      * 'warmUp' - the device shall transition from the 'standby' mode
        to the 'ready' mode - invalid from any other power mode
        (optional command for remote device power management).
      * 'coolDown' - the device shall transition from the 'ready' mode
        to the 'standby' mode - invalid from any other power mode
        (optional command for remote device power management).
      * 'energySave' - the device shall transition from the 'standby'
        mode to the 'sleep' mode - invalid from any other power mode
        (optional command for remote device power management).
      * 'wakeUp' - the device shall transition from the 'sleep'
        mode to the 'standby' mode - invalid from any other power mode
        (optional command for remote device power management).
      * 'powerToReady' - the device shall transition from the 'standby'
        mode or the 'sleep' mode to the 'ready' mode
        (optional command for remote device power management).
      * 'powerToStandby' - the device shall transition from the 'ready'
        mode or the 'sleep' mode to the 'standby' mode
        (optional command for remote device power management).
      * 'powerToSleep' - the device shall transition from the 'ready'
        mode or the 'standby' mode to the 'sleep' mode
        (optional command for remote device power management).

        Note:   All of the POSIX and XCMI device level operations are
        taken from the POSIX System Admin std (IEEE 1387.4) and aligned
        with the high-end XCMI System Admin MIB."
    REFERENCE
        "See:   'dot5Commands' in IEEE 802.5 Token Ring MIB (RFC 1748)
        and 'hrDeviceStatus' in IETF Host Resources MIB (RFC 1514).
        Compare:    'ifOperStatus' (current) and 'ifAdminStatus'
        (desired) in the Interfaces Group of IETF MIB-II (RFC 1213);
        'RowStatus' textual convention in IETF SMIv2 (RFC 1442/1902).

        See:    Section 4 'Print Utilities' (pages 71 to 212) of
                POSIX Sys Admin (IEEE 1387.4 / Draft 8, October 1994).
        See:    OBJECT clause in MODULE-COMPLIANCE macro of
                XCMI Host Resources Ext MIB, for compliance info."
    SYNTAX      INTEGER {


        none(1),                        -- no operation
        startup(2),                     -- to 'running'
        resetWarning(3),                -- from 'warning' to 'running'
        test(4),                        -- to 'testing' immediately
        shutdown(5),                    -- to 'down' immediately
        quiesce(6),                     -- to 'down' gracefully
        resetCounters(7),               -- reset all device counters
        resetWarm(8),                   -- warm restart to 'running'
        resetCold(9),                   -- cold restart to 'running'
        resetFactory(10),               -- factory defaults cold restart
        flushInput(11),                 -- flush all input
        flushOutput(12),                -- flush all output
        flushInOut(13),                 -- flush all input and output
        manage(14),                     -- manage command, any state
        refresh(15),                    -- refresh device w/out reset
        warmUp(16),                     -- 'standby' to 'ready' ONLY
        coolDown(17),                   -- 'ready' to 'standby' ONLY
        energySave(18),                 -- 'standby' to 'sleep' ONLY
        wakeUp(19),                     -- 'sleep' to 'standby' ONLY
        powerToReady(20),               -- 'standby|sleep' to 'ready'
        powerToStandby(21),             -- 'ready|sleep' to 'standby'
        powerToSleep(22),               -- 'ready|standby' to 'sleep'
        --  POSIX - Device level operations (on host system)
        deviceCreate(1301),             -- 'pdcreate' (create device)
        deviceDelete(1302),             -- 'pddelete' (delete device)
        deviceList(1303),               -- 'pdls' (list svc attributes)
        deviceSet(1304),                -- 'pdset' (set svc attributes)
        deviceClean(1305),              -- 'pdclean' (remove all jobs)
        deviceDisable(1306),            -- 'pddisable' (stop new jobs)
        deviceEnable(1307),             -- 'pdenable' (allow new jobs)
        devicePause(1308),              -- 'pdpause' (pause device)
        deviceResume(1309),             -- 'pdresume' (resume device)
        deviceShutdown(1310),           -- 'pdshutdown' (end device)
        deviceQueueList(1311),          -- 'pdq' (list device job queue)
        --  XCMI - Device level extensions (on host system)
        deviceManage(2301),             -- manage device object(s)
        deviceRestart(2302),            -- restart device
        deviceInstall(2321),            -- install device object(s)
        deviceUpgrade(2322),            -- upgrade device object(s)
        deviceBackup(2323),             -- backup device object(s)
        deviceRestore(2324),            -- restore device object(s)
        deviceConfigure(2325),          -- configure device object(s)
        deviceDiagnose(2326),           -- diagnose device object(s)
        deviceResetCounters(2331),      -- reset device counters
        deviceResetWarm(2332),          -- warm reset (no power cycle)
        deviceResetCold(2333),          -- cold reset (w/ power cycle)
        deviceResetFactory(2334),       -- factory defaults reset
        deviceLogin(2341),              -- login w/ authentication
        deviceLogout(2342)              -- logout w/ authentication
    }


XcmHrDevMgmtCommandData ::= TEXTUAL-CONVENTION
    STATUS      current
    DESCRIPTION
        "A write of this type specifies:  a) a 'test' command subtype
        and any accompanying 'test' device specific data; or b) a
        'manage' command subtype and any accompanying 'manage' device
        specific data; or c) device specific data accompanying any
        other command.
        A read of this type always returns the data (if any) which
        accompanied the current or last completed command."
    REFERENCE
        "See:   Appropriate standards for device specific tests"
    SYNTAX      OCTET STRING (SIZE (0..255))

XcmHrDevPowerModeType ::= TEXTUAL-CONVENTION
    STATUS      current
    DESCRIPTION
        "A device power mode type, used by system administrators
        of this device for power management details.

        Usage:  Used in 'devicePowerModeType' Device Detail, to clearly
        identify the referenced power mode (without resort to strings)."
    SYNTAX      INTEGER {
        other(1),                       -- other power mode type
        unknown(2),                     -- unknown power mode type
        --  XCMI simple device power modes, supported in
        --  Device Calendar, Device Mgmt, and Device Power groups via
        --  'XcmHrDevMgmtCommandRequest' and 'XcmHrDevInfoConditions'
        readyMode(3),                   -- 'warmUp|powerToReady' in
                                        -- 'XcmHrDevMgmtCommandRequest'
        standbyMode(4),                 -- 'coolDown|powerToStandby' in
                                        -- 'XcmHrDevMgmtCommandRequest'
        sleepMode(5),                   -- 'energySave|powerToSleep' in
                                        -- 'XcmHrDevMgmtCommandRequest'
        offMode(6)                      -- 'shutdown|quiesce' in
                                        -- 'XcmHrDevMgmtCommandRequest'
        --  XCMI advanced device power modes, supported in
        --  Device Detail group via
        --  'XcmHrDevDetailType' of 'devicePowerModeType'
        --  ...to be supplied
    }

XcmHrDevPowerTimeUnit ::= TEXTUAL-CONVENTION
    STATUS      current
    DESCRIPTION
        "A device power cycle time unit, used by system administrators
        of this device for power management cycle times.

        Usage:  Used to scale the values in the Device Power group, for
        convenience and (optional) high resolution."
    SYNTAX      INTEGER {
        other(1),                       -- other time unit
        unknown(2),                     -- unknown time unit
        microsecond(3),                 -- 1 microsecond


        millisecond(4),                 -- 1 millisecond
        second(5),                      -- 1 second
        kilosecond(6),                  -- 1 kilosecond
        megasecond(7),                  -- 1 megasecond
        minute(8),                      -- 1 minute
        hour(9),                        -- 1 hour
        day(10),                        -- 1 day
        week(11),                       -- 1 week
        month(12),                      -- 1 month
        year(13)                        -- 1 year
    }

XcmHrDevTrafficUnit ::= TEXTUAL-CONVENTION
    STATUS      current
    DESCRIPTION
        "The type of traffic unit used to measure input and/or output
        traffic for this device.

        Usage:  The use of either 'other' or 'unknown' is uninformative
        and should be avoided by conforming implementations."
    SYNTAX      INTEGER {
        other(1),                       -- other traffic unit         
        unknown(2),                     -- unknown traffic unit       
        binaryBit(11),                  -- 1 bit
        binaryNibble(12),               -- 4 bits
        binaryOctet(13),                -- 8 bits
        binaryLine(14),                 -- 1 to N bits (eg, video line)
        textCharacter(15),              -- 5 to 8 bits
        textWord(16),                   -- 1 to N characters
        textLine(17),                   -- 1 to N characters
        textSentence(18),               -- 1 to N words
        textParagraph(19),              -- 1 to N sentences
        mediaBlock(20),                 -- 1 media-specific block
        mediaSector(21),                -- 1 media-specific sector
        mediaRow(22),                   -- 1 media-specific row
        mediaColumn(23),                -- 1 media-specific column
        mediaPacket(24),                -- 1 media-specific packet
        mediaCell(25),                  -- 1 media-specific cell
        mediaImage(26),                 -- 1 media-specific image
        mediaImpression(27),            -- 1 media-specific impression
        mediaSheet(28),                 -- 1 media-specific sheet
        lengthInch(29),                 -- 1 English inch
        lengthFoot(30),                 -- 1 English foot
        lengthYard(31),                 -- 1 English yard
        lengthMile(32),                 -- 1 English mile
        lengthMicrometer(33),           -- 1 micrometer
        lengthMillimeter(34),           -- 1 millimeter
        lengthCentimeter(35),           -- 1 centimeter
        lengthMeter(36),                -- 1 meter
        lengthKilometer(37)             -- 1 kilometer
    }


XcmHrGroupSupport ::= TEXTUAL-CONVENTION
    STATUS      current
    DESCRIPTION
        "The terse conformance statement of ALL mandatory, conditionally
        mandatory, and optional IETF Host Resources MIB (RFC 1514)
        and XCMI Host Resources Extensions MIB objects which are
        supported by this management agent implementation (ie, version)
        on this host system, specified in a bit-mask.

        The current set of values (which may be extended in the future)
        is given below:

        --  IETF Host Resources MIB object groups
              1 : hrSystemGroup               -- 2**0
              2 : hrStorageGroup              -- 2**1
              4 : hrDeviceGroup               -- 2**2
              8 : hrSWRunGroup                -- 2**3
             16 : hrSWRunPerfGroup            -- 2**4
             32 : hrSWInstalledGroup          -- 2**5
        --  XCMI Host Resources Ext MIB object groups
             64 : xcmHrDevInfoGroup           -- 2**6
            128 : xcmHrDevHelpGroup           -- 2**7
            256 : xcmHrDevMgmtGroup           -- 2**8
            512 : xcmHrDevPowerGroup          -- 2**9
           1024 : xcmHrDevTrafficGroup        -- 2**10
           2048 : xcmHrSystemFaultGroup       -- 2**11
           4096 : xcmHrGeneralGroup           -- 2**12
           8192 : xcmHrDevCalendarGroup       -- 2**13
          16384 : xcmHrSWRunGroup             -- 2**14
          32768 : xcmHrSWInstalledGroup       -- 2**15
          64536 : xcmHrDevDetailGroup         -- 2**16
         131072 : xcmHrStorageExtGroup        -- 2**17
         262144 : xcmHrStorageDetailGroup     -- 2**18
        --  IETF Host Resources MIB tables for specific device types
       33554432 : hrProcessorTable            -- 2**25
       67108864 : hrNetworkTable              -- 2**26
      134217728 : hrPrinterTable              -- 2**27
      268435456 : hrDiskStorageTable          -- 2**28
      536870912 : hrPartitionTable            -- 2**29
     1073741824 : hrFSTable                   -- 2**30

        -- 2**31 not used, due to 'Integer32|Cardinal32' semantics

        Usage:  Conforming management agents shall ALWAYS accurately
        report their support for IETF Host Resources MIB (RFC 1514)
        and XCMI Host Resources Extensions MIB object groups."
    SYNTAX      INTEGER (0..2147483647)  -- biggest int = 2**31-1

XcmHrSWRunXStatus ::= TEXTUAL-CONVENTION
    STATUS      current
    DESCRIPTION
        "An extended software status, used by system administrators and
        end users of this software (here, read 'state' for 'status').


        Note:   This extended software status is present for future
        extensions."
    REFERENCE
        "See:   'hrSWRunStatus' in the basic Software Running Group
        of the IETF Host Resources MIB (RFC 1514)."
    SYNTAX      INTEGER {
        none(0),
        other(1),
        unknown(2)
    }

XcmHrStorageDetailType ::= TEXTUAL-CONVENTION
    STATUS      current
    DESCRIPTION
        "The type of the storage detail information specified
        in this conceptual row in the 'xcmHrStorageDetailTable'.

        Usage:  Used to describe system-, program-, or thread-level
        memory allocations/reservations.

        Usage:  'hrStorageEntry' and (optionally) 'xcmHrStorageEntry'
        may be referenced via 'xcmSecServiceHrStorageIndex' in the
        Service group of the XCMI Security MIB.

      * 'other'
      * 'unknown'

        --  Storage general info
      * 'storageName'
        - storage administrative name in directory (primary name)
        - type - '...ValueOID' (directory in XCMI Comms Config TC)
        - (eg, 'xcmCONetwareNDS')
        - data - '...ValueString'
        - (eg, 'showstopper')
      * 'storageAlias'
        - storage administrative alias in directory (alternate name)
        - type - '...ValueOID' (directory in XCMI Comms Config TC)
        - (eg, 'xcmCONetwareNDS')
        - data - '...ValueString'
        - (eg, 'LaserRat')
      * 'storageType'
        - storage type (read-write/read-create)
        - see - 'hrStorageType' in IETF HR MIB
        - type - (OBJECT IDENTIFIER)
        - data - '...ValueOID'
        - (eg, 'hrStorageRam')
      * 'storageDescription'
        - storage description (read-write/read-create)
        - see - 'hrStorageDescr' in IETF HR MIB
        - type - (DisplayString)
        - data - '...ValueString'
        - (eg, 'Kingston 16MB...')
      * 'storageAllocationUnits'


        - storage allocation block size (in octets)
        - type - 'hrStorageAllocationUnits'
        - data - '...ValueInteger'
        - (eg, '4096')
      * 'storageTree'
        - storage tree prefix to name/alias in directory
        - type - '...ValueOID' (directory in XCMI Comms Config TC)
        - (eg, 'xcmCONetwareNDS')
        - data - '...ValueString'
        - (may also appear in 'storageName')
      * 'storageContext'
        - storage context prefix to name/alias in directory
        - type - '...ValueOID' (directory in XCMI Comms Config TC)
        - (eg, 'xcmCONetwareNDS')
        - data - '...ValueString'
        - (may also appear in 'storageName')

        --  System/Program/Thread storage details
      * 'storageInputBuffer'
        - network or standard input buffer size
        - type - (Cardinal32)
        - data - '...ValueInteger'
        - positive integer = size in 'hrStorageAllocationUnits'
        - zero = no size specified
      * 'storageOutputBuffer'
        - network or standard output buffer size
        - type - (Cardinal32)
        - data - '...ValueInteger'
        - positive integer = size in 'hrStorageAllocationUnits'
        - zero = no size specified
      * 'storageImageBuffer'
        - frame buffer size
        - type - (Cardinal32)
        - data - '...ValueInteger'
        - positive integer = size in 'hrStorageAllocationUnits'
        - zero = no size specified
      * 'storageMarkerBuffer'
        - marker buffer size (for hardcopy)
        - type - (Cardinal32)
        - data - '...ValueInteger'
        - positive integer = size in 'hrStorageAllocationUnits'
        - zero = no size specified
      * 'storagePageBuffer'
        - interpreter buffer size (for softcopy)
        - type - (Cardinal32)
        - data - '...ValueInteger'
        - positive integer = size in 'hrStorageAllocationUnits'
        - zero = no size specified
      * 'storageTranslationBuffer'
        - translation/localization buffer size
        - type - (Cardinal32)
        - data - '...ValueInteger'
        - positive integer = size in 'hrStorageAllocationUnits'
        - zero = no size specified


      * 'storageWorkingBuffer'
        - working buffer size
        - type - (Cardinal32)
        - data - '...ValueInteger'
        - positive integer = size in 'hrStorageAllocationUnits'
        - zero = no size specified

        --  Interpreter storage details
      * 'storageFontCache'
        - interpreter font cache size
        - type - (Cardinal32)
        - data - '...ValueInteger'
        - positive integer = size in 'hrStorageAllocationUnits'
        - zero = no size specified
      * 'storageFormCache'
        - interpreter form cache size
        - type - (Cardinal32)
        - data - '...ValueInteger'
        - positive integer = size in 'hrStorageAllocationUnits'
        - zero = no size specified
      * 'storageLogoCache'
        - interpreter logo cache size
        - type - (Cardinal32)
        - data - '...ValueInteger'
        - positive integer = size in 'hrStorageAllocationUnits'
        - zero = no size specified
      * 'storageMacroCache'
        - interpreter macro cache size
        - type - (Cardinal32)
        - data - '...ValueInteger'
        - positive integer = size in 'hrStorageAllocationUnits'
        - zero = no size specified
      * 'storageStyleCache'
        - interpreter style cache size
        - type - (Cardinal32)
        - data - '...ValueInteger'
        - positive integer = size in 'hrStorageAllocationUnits'
        - zero = no size specified

        --  Program/Thread storage details
      * 'storageHeapMemory'
        - program/thread heap memory size
        - type - (Cardinal32)
        - data - '...ValueInteger'
        - positive integer = size in 'hrStorageAllocationUnits'
        - zero = no size specified
      * 'storagePrefixMemory'
        - program/thread prefix memory size
        - type - (Cardinal32)
        - data - '...ValueInteger'
        - positive integer = size in 'hrStorageAllocationUnits'
        - zero = no size specified
      * 'storageStackMemory'
        - program/thread stack memory size


        - type - (Cardinal32)
        - data - '...ValueInteger'
        - positive integer = size in 'hrStorageAllocationUnits'
        - zero = no size specified
      * 'storageWorkingMemory'
        - program/thread working memory size
        - type - (Cardinal32)
        - data - '...ValueInteger'
        - positive integer = size in 'hrStorageAllocationUnits'
        - zero = no size specified

        --  Storage addressing details
      * 'storageBaseAddress'
        - storage base address (physical or logical)
        - type - (Cardinal)
        - data - '...ValueInteger'
        - (eg, '0xF800')
      * 'storageWordSize'
        - storage addressability (word size in octets)
        - type - (Cardinal32)
        - data - '...ValueInteger'
        - (eg, '4')
      * 'storagePageSize'
        - storage page size (in octets)
        - type - (Cardinal32)
        - data - '...ValueInteger'
        - (eg, '8192')

        Usage:  Conforming management stations and management agents
        shall implement the above semantics for service detail types."
    REFERENCE
        "See:   'xcmHrStorageDetailUnit' for units of storage detail."
    SYNTAX      INTEGER {
        other(1),
        unknown(2),
        --  Storage general info
        storageName(3),                 -- storage name (primary name)
        storageAlias(4),                -- storage alias (other name)
        storageType(5),                 -- storage type (R/W)
        storageDescription(6),          -- storage description (R/W)
        storageAllocationUnits(7),      -- storage allocation block size
        storageTree(8),                 -- storage directory tree
        storageContext(9),              -- storage context
        --  System/Program/Thread storage details
        storageInputBuffer(10),         -- network or standard input
        storageOutputBuffer(11),        -- network or standard output
        storageImageBuffer(12),         -- frame buffer
        storageMarkerBuffer(13),        -- marker buffer (hardcopy)
        storagePageBuffer(14),          -- interpreter buffer (softcopy)
        storageTranslationBuffer(15),   -- translate/localize buffer
        storageWorkingBuffer(16),       -- working buffer
        --  Interpreter storage details
        storageFontCache(20),           -- interpreter font cache
        storageFormCache(21),           -- interpreter form cache


        storageLogoCache(22),           -- interpreter logo cache
        storageMacroCache(23),          -- interpreter macro cache
        storageStyleCache(24),          -- interpreter style cache
        --  Program/Thread storage details
        storageHeapMemory(30),          -- program/thread heap memory
        storagePrefixMemory(31),        -- program/thread prefix memory
        storageStackMemory(32),         -- program/thread stack memory
        storageWorkingMemory(33),       -- program/thread working memory
        --  Storage addressing details
        storageBaseAddress(40),         -- storage base address
        storageWordSize(41),            -- storage addressability
        storagePageSize(42)             -- storage page size
    }

XcmHrStorageRealization ::= TEXTUAL-CONVENTION
    STATUS      current
    DESCRIPTION
        "An extended storage type (or storage 'realization'),
        used by system administrators and end users of this storage.

        Usage:  The use of either 'other' or 'unknown' is uninformative
        and should be avoided by conforming implementations.

      * 'physicalSystem' - 'real' memory installed on a 'system'
        whose product is found via 'xcmHrStorageProductDeviceIndex' and
        whose CPU is found via 'xcmHrStoragePlatformDeviceIndex' and
        whose self is found via 'xcmHrStorageMatchingDeviceIndex';
      * 'physicalProgram' - 'real' memory assigned to a 'program'
        (memory which is 'pinned' and is NOT paged to disk storage)
        whose program is found via 'xcmHrStorageSWRunIndex';
      * 'physicalThread' - 'real' memory assigned to a 'thread'
        (memory which is 'pinned' and is NOT paged to disk storage)
        whose program/thread is found via 'xcmHrStorageSWRunIndex';
      * 'logicalSystem' - 'virtual' memory assigned to a 'system'
        (memory which is NOT 'pinned' and MAY be paged to disk storage)
        whose product is found via 'xcmHrStorageProductDeviceIndex' and
        whose CPU is found via 'xcmHrStoragePlatformDeviceIndex' and
        whose self is found via 'xcmHrStorageMatchingDeviceIndex';
      * 'logicalProgram' - 'virtual' memory assigned to a 'program'
        (memory which is NOT 'pinned' and MAY be paged to disk storage)
        whose program is found via 'xcmHrStorageSWRunIndex';
      * 'logicalThread' - 'virtual' memory assigned to a 'thread'
        (memory which is NOT 'pinned' and MAY be paged to disk storage)
        whose program/thread is found via 'xcmHrStorageSWRunIndex'."
    REFERENCE
        "See:   'XcmHrDevInfoRealization' textual convention in
                the XCMI Host Resources Ext TC.
        See:    'xcmHrDevInfoRealization' in the Device Info group of
                the XCMI Host Resources Ext MIB."
    SYNTAX      INTEGER {
        other(1),                       -- other storage       
        unknown(2),                     -- unknown storage     
        physicalSystem(10),             -- 'real' system storage
        physicalProgram(11),            -- 'real' program storage


        physicalThread(12),             -- 'real' thread storage
        logicalSystem(20),              -- 'virtual' system storage
        logicalProgram(21),             -- 'virtual' program storage
        logicalThread(22)               -- 'virtual' thread storage
    }

XcmHrDpaAvailability ::= TEXTUAL-CONVENTION
    STATUS      current
    DESCRIPTION
        "The generic availability of this system, device, service, etc."
    REFERENCE
        "See:   Section 9.1.6.6 '[Generic attribute] Availability' and
                Annex A 'id-val-availability-...'
                in DPA (ISO/IEC 10175-1 Final Text, March 1996)."
    --  The following enum values are identical to the final arcs of
    --  the ISO DPA 'id-val-availability-...' OIDs
    SYNTAX      INTEGER {
        high(1),
        normal(2),
        low(3),
    --  none(5),
        unknown(6)
    }

XcmHrDpaConditions ::= TEXTUAL-CONVENTION
    STATUS      current
    DESCRIPTION
        "The generic conditions (ie, state reasons) of this system,
        device, service, etc.

              1 : cleanedByOperator
              2 : cleanedBySystem
              4 : disabledByOperator
              8 : disabledBySystem
             16 : pausedByOperator
             32 : pausedBySystem
             64 : shutdownByOperator
            128 : shutdownBySystem
            256 : diagnosedByOperator
            512 : diagnosedBySystem
           1024 : resetByOperator
           2048 : resetBySystem

        Usage:  The above 'conditions' augment the service state in
        'xcmSvcMonService[Current|Previous]State' and the service mgmt
        information in 'xcmSvcMonServiceMgmt[Operation|InProgress]'.

        Usage:  Conforming management agents shall ALWAYS report all
        'conditions' of entities accurately.  'Conditions' occur within
        or across 'states' in a finite state machine implementation of a
        system, device, service, etc.

        Usage:  A service with 'xcmSvcMonServiceCurrentState' of
        'ready(1)' might have 'xcmSvcMonServiceConditions' of


        'disabledByOperator', indicating that the service will not
        accept new jobs.

        Usage:  A multi-bit example of 'xcmSvcMonServiceConditions' is
        'disabledByOperator' concurrently with 'pausedByOperator'."
    REFERENCE
        "See:   Section 9.5.4 'Server-state',
                section 9.1.6.4 '[Generic attribute] State', and
                Annex A 'id-val-state-...'
                in DPA (ISO/IEC 10175-1 Final Text, March 1996).
        See:    Section D.2.3 'Server State Transitions'
                in DPA Mgmt Service (ISO 10175-3 Draft, October 1996)."
    SYNTAX      INTEGER (0..2147483647)  -- biggest int = 2**31-1

XcmHrDpaJobValidateSupport ::= TEXTUAL-CONVENTION
    STATUS      current
    DESCRIPTION
        "The job validation support of this system, service, etc.

        The current set of values (which may be extended in the future)
        is given below:

            --  ISO DPA standard values
              1 : validateAndProcess    -- generalized from DPA 'print'
              2 : validateSubmitOnly    -- error check, do NOT process
            --  XCMI standard values
              4 : validateSyntaxOnly    -- check syntax only
              8 : validateSemanticsOnly -- check syntax/ranges/states
             16 : validateLocalOnly     -- check semantic/local services
             32 : validateDistributed   -- check distributed services
             64 : validateCreateLocal   -- create local child jobs
            128 : validateCreateRemote  -- create remote child jobs

        Usage:  Conforming management agents shall ALWAYS accurately
        report their support for job validation modes."
    REFERENCE
        "See:   Section 9.5.10 'Job-validates-supported' (server),
                section 9.2.4.12 'Job-validate' (job), and
                Annex A 'id-val-job-validate-...'
                in DPA (ISO/IEC 10175-1 Final Text, March 1996)."
    SYNTAX      INTEGER (0..2147483647)  -- biggest int = 2**31-1

XcmHrDpaObjectClassSupport ::= TEXTUAL-CONVENTION
    STATUS      current
    DESCRIPTION
        "The object class support of this system, service, etc.

        The current set of values (which may be extended in the future)
        is given below:

            --  ISO DPA standard values
              1 : generic               -- 2**0
              2 : job                   -- 2**1
              4 : printer               -- 2**2


              8 : server                -- 2**3
             16 : medium                -- 2**4
             32 : font                  -- 2**5
            256 : transferMethod        -- 2**8
            512 : deliveryMethod        -- 2**9
           1024 : auxiliarySheet        -- 2**10
           2048 : finishing             -- 2**11
           4096 : output                -- 2**12
           8192 : imposition            -- 2**13
          16384 : scheduler             -- 2**14
          32768 : document              -- 2**15
          65536 : resource              -- 2**16
         131072 : initialValueJob       -- 2**17
         262144 : initialValueDocument  -- 2**18
         524288 : resourceContext       -- 2**19
        1048576 : auxiliarySheetPackage -- 2**20
            --  XCMI standard values
       16777216 : deviceHostSystem      -- 2**24
       33554432 : deviceScanner         -- 2**25
       67108864 : deviceCopier          -- 2**26
      134217728 : deviceFax             -- 2**27
      268435456 : deviceMailbox         -- 2**28
      536870912 : deviceFinisher        -- 2**29
     1073741824 : deviceCRU             -- 2**30

        -- 2**31 not used, due to 'Integer32|Cardinal32' semantics

        Usage:  Conforming management agents shall ALWAYS accurately
        report their support for object classes (ISO DPA and XCMI)."
    REFERENCE
        "See:   Section 9.5.5 'Object-classes-supported' (server),
                section 9.1.6.1 'Object-class' (system),
                Annex A 'id-oc-...'
                in DPA (ISO/IEC 10175-1 Final Text, March 1996)."
    SYNTAX      INTEGER (0..2147483647)  -- biggest int = 2**31-1

XcmHrDpaState ::= TEXTUAL-CONVENTION
    STATUS      current
    DESCRIPTION
        "The generic state of this system, device, service, etc."
    REFERENCE
        "See:   Section 9.1.6.4 '[Generic attribute] State' and
                Annex A 'id-val-state-...'
                in DPA (ISO/IEC 10175-1 Final Text, March 1996)."
    --  The following enum values are identical to the final arcs of
    --  the ISO DPA 'id-val-state-...' OIDs
    SYNTAX      INTEGER {
        ready(1),
        onRequest(2),
        unavailable(3),
        unknown(4),
        busy(5),
        initializing(6),
        terminating(7)


    }

--
--          The HRX TC Dummy Group (DO NOT USE)
--
--          DO NOT USE - Present to suppress compiler warnings ONLY!
--
--          Note:  The following objects have 'odd' use of case in their
--          names (ie, 'xCm...'), in order to make obvious their related
--          textual conventions

xCmHrDummy          OBJECT IDENTIFIER ::= { xcmHrTC 999 }

xCmHrDevCalendarDayOfWeek OBJECT-TYPE
    SYNTAX      XcmHrDevCalendarDayOfWeek
    MAX-ACCESS  not-accessible
    STATUS      current
    DESCRIPTION "Dummy - DO NOT USE"
    ::= { xCmHrDummy 1 }

xCmHrDevCalendarTimeOfDay OBJECT-TYPE
    SYNTAX      XcmHrDevCalendarTimeOfDay
    MAX-ACCESS  not-accessible
    STATUS      current
    DESCRIPTION "Dummy - DO NOT USE"
    ::= { xCmHrDummy 2 }

xCmHrDevDetailType OBJECT-TYPE
    SYNTAX      XcmHrDevDetailType
    MAX-ACCESS  not-accessible
    STATUS      current
    DESCRIPTION "Dummy - DO NOT USE"
    ::= { xCmHrDummy 3 }

xCmHrDevDetailUnitClass OBJECT-TYPE
    SYNTAX      XcmHrDevDetailUnitClass
    MAX-ACCESS  not-accessible
    STATUS      current
    DESCRIPTION "Dummy - DO NOT USE"
    ::= { xCmHrDummy 4 }

xCmHrDevInfoRealization OBJECT-TYPE
    SYNTAX      XcmHrDevInfoRealization
    MAX-ACCESS  not-accessible
    STATUS      current
    DESCRIPTION "Dummy - DO NOT USE"
    ::= { xCmHrDummy 5 }

xCmHrDevInfoStatus OBJECT-TYPE
    SYNTAX      XcmHrDevInfoStatus
    MAX-ACCESS  not-accessible
    STATUS      current
    DESCRIPTION "Dummy - DO NOT USE"
    ::= { xCmHrDummy 6 }


xCmHrDevInfoXStatus OBJECT-TYPE
    SYNTAX      XcmHrDevInfoXStatus
    MAX-ACCESS  not-accessible
    STATUS      current
    DESCRIPTION "Dummy - DO NOT USE"
    ::= { xCmHrDummy 7 }

xCmHrDevInfoConditions OBJECT-TYPE
    SYNTAX      XcmHrDevInfoConditions
    MAX-ACCESS  not-accessible
    STATUS      current
    DESCRIPTION "Dummy - DO NOT USE"
    ::= { xCmHrDummy 8 }

xCmHrDevInfoXConditions OBJECT-TYPE
    SYNTAX      XcmHrDevInfoXConditions
    MAX-ACCESS  not-accessible
    STATUS      current
    DESCRIPTION "Dummy - DO NOT USE"
    ::= { xCmHrDummy 9 }

xCmHrDevMgmtCommandRequest OBJECT-TYPE
    SYNTAX      XcmHrDevMgmtCommandRequest
    MAX-ACCESS  not-accessible
    STATUS      current
    DESCRIPTION "Dummy - DO NOT USE"
    ::= { xCmHrDummy 10 }

xCmHrDevMgmtCommandData OBJECT-TYPE
    SYNTAX      XcmHrDevMgmtCommandData
    MAX-ACCESS  not-accessible
    STATUS      current
    DESCRIPTION "Dummy - DO NOT USE"
    ::= { xCmHrDummy 11 }

xCmHrDevPowerModeType OBJECT-TYPE
    SYNTAX      XcmHrDevPowerModeType
    MAX-ACCESS  not-accessible
    STATUS      current
    DESCRIPTION "Dummy - DO NOT USE"
    ::= { xCmHrDummy 12 }

xCmHrDevPowerTimeUnit OBJECT-TYPE
    SYNTAX      XcmHrDevPowerTimeUnit
    MAX-ACCESS  not-accessible
    STATUS      current
    DESCRIPTION "Dummy - DO NOT USE"
    ::= { xCmHrDummy 13 }

xCmHrDevTrafficUnit OBJECT-TYPE
    SYNTAX      XcmHrDevTrafficUnit
    MAX-ACCESS  not-accessible
    STATUS      current


    DESCRIPTION "Dummy - DO NOT USE"
    ::= { xCmHrDummy 14 }

xCmHrGroupSupport OBJECT-TYPE
    SYNTAX      XcmHrGroupSupport
    MAX-ACCESS  not-accessible
    STATUS      current
    DESCRIPTION "Dummy - DO NOT USE"
    ::= { xCmHrDummy 15 }

xCmHrSWRunXStatus OBJECT-TYPE
    SYNTAX      XcmHrSWRunXStatus
    MAX-ACCESS  not-accessible
    STATUS      current
    DESCRIPTION "Dummy - DO NOT USE"
    ::= { xCmHrDummy 16 }

xCmHrStorageDetailType OBJECT-TYPE
    SYNTAX      XcmHrStorageDetailType
    MAX-ACCESS  not-accessible
    STATUS      current
    DESCRIPTION "Dummy - DO NOT USE"
    ::= { xCmHrDummy 17 }

xCmHrStorageRealization OBJECT-TYPE
    SYNTAX      XcmHrStorageRealization
    MAX-ACCESS  not-accessible
    STATUS      current
    DESCRIPTION "Dummy - DO NOT USE"
    ::= { xCmHrDummy 18 }

xCmHrDpaAvailability OBJECT-TYPE
    SYNTAX      XcmHrDpaAvailability
    MAX-ACCESS  not-accessible
    STATUS      current
    DESCRIPTION "Dummy - DO NOT USE"
    ::= { xCmHrDummy 19 }

xCmHrDpaConditions OBJECT-TYPE
    SYNTAX      XcmHrDpaConditions
    MAX-ACCESS  not-accessible
    STATUS      current
    DESCRIPTION "Dummy - DO NOT USE"
    ::= { xCmHrDummy 20 }

xCmHrDpaJobValidateSupport OBJECT-TYPE
    SYNTAX      XcmHrDpaJobValidateSupport
    MAX-ACCESS  not-accessible
    STATUS      current
    DESCRIPTION "Dummy - DO NOT USE"
    ::= { xCmHrDummy 21 }

xCmHrDpaObjectClassSupport OBJECT-TYPE
    SYNTAX      XcmHrDpaObjectClassSupport


    MAX-ACCESS  not-accessible
    STATUS      current
    DESCRIPTION "Dummy - DO NOT USE"
    ::= { xCmHrDummy 22 }

xCmHrDpaState OBJECT-TYPE
    SYNTAX      XcmHrDpaState
    MAX-ACCESS  not-accessible
    STATUS      current
    DESCRIPTION "Dummy - DO NOT USE"
    ::= { xCmHrDummy 23 }

END
