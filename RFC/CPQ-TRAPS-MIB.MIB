CPQ-TRAPS-MIB DEFINITIONS ::= BEGIN

	IMPORTS
        mib-2		
        	FROM RFC1213-MIB
        TRAP-TYPE	
        	FROM RFC-1215
		enterprises 
			FROM RFC1155-SMI
		compaq                         
			FROM CPQHOST-MIB
		compaq-common-mgmt
			FROM COMPAQ-ID-REC
		cpqRackUid,
		cpqRackCommonEnclosureSerialNum,
		cpqRackNetConnectorSerialNum,
		cpqRackName,
		cpqRackCommonEnclosureName,           
		cpqRackNetConnectorName,
		cpqRackNetConnectorLocation,
		cpqRackNetConnectorFWRev,
		cpqRackNetConnectorSparePartNumber	 	
			FROM CPQRACK
		agentBscSwFileAddr,
		agentBscSwFile,                              
		agentBscSwFileLoadType,
		agentBscSwFileStatus,
		agentSNTPServer1IPAddr,
		agentSNTPServer2IPAddr,
		agentSwitchFanIndex,
		agentSwitchFanCondition,
		agentSwitchTempSensorIndex,
		agentSwitchTempSensorCurrent,
        agentSwitchTempSensorThreshold,
        agentSwitchTempSensorCondition,
        agentSwitchTempSensorTempType,
		agentSwitchPowerSupplyMaxPwrOutput,
        agentSwitchPowerSupplyCurPwrOutput,
        agentSwitchPowerSupplyIntakeTemp,
 		agentSwitchPowerSupplyExhaustTemp,
        agentSwitchPowerSupplyStatus,
        agentSwitchPowerSupplyInputLineStatus,
        agentSwitchPowerSupplyCondition,
        agentSwitchCubeType,
    	agentSwitchCubeSpareName,
    	agentSwitchCubeSparePartNumber
			FROM COMPAQ-AGENT		
		;		
		
	--
	-- The traps defined in RFC2737
	--
	-- Entity MIB Trap Definitions
	entityMIB			OBJECT IDENTIFIER ::= { mib-2 47 }
	entityMIBTraps      OBJECT IDENTIFIER ::= { entityMIB 2 }
	entityMIBTrapPrefix OBJECT IDENTIFIER ::= { entityMIBTraps 0 }

	entConfigChange TRAP-TYPE
		ENTERPRISE  entityMIBTrapPrefix
		DESCRIPTION
           "An entConfigChange notification is generated when the value
            of entLastChangeTime changes. It can be utilized by an NMS
            to trigger logical/physical entity table maintenance polls.

            An agent should not generate more than one entConfigChange
            'notification-event' in a given time interval (five seconds
            is the suggested default).  A 'notification-event' is the
            transmission of a single trap or inform PDU to a list of
            notification destinations.

            If additional configuration changes occur within the
            throttling period, then notification-events for these
            changes should be suppressed by the agent until the current
            throttling period expires.  At the end of a throttling
            period, one notification-event should be generated if any
            configuration changes occurred since the start of the
            throttling period. In such a case, another throttling period
            is started right away.

            An NMS should periodically check the value of
            entLastChangeTime to detect any missed entConfigChange
            notification-events, e.g., due to throttling or transmission
            loss."
            
            	--#SEVERITY INFORMATIONAL
	::= 1
	
	switchFirmwareTransferred TRAP-TYPE
		ENTERPRISE compaq
		VARIABLES  {
			cpqRackUid,
			cpqRackCommonEnclosureSerialNum,
			cpqRackNetConnectorSerialNum,
			cpqRackName,
			cpqRackCommonEnclosureName,           
			cpqRackNetConnectorName,
			cpqRackNetConnectorLocation,
			agentBscSwFileAddr,
			agentBscSwFile,                              
			agentBscSwFileLoadType,
			cpqRackNetConnectorFWRev 			
		}

		DESCRIPTION
		"The switch has successfully transferred a firmware image."
		
			 --#SEVERITY INFORMATIONAL
			 
	::= 161001


	switchConfigFileTransferred TRAP-TYPE
		ENTERPRISE compaq
		VARIABLES  {
	 		cpqRackUid,
	 		cpqRackCommonEnclosureSerialNum,
	 		cpqRackNetConnectorSerialNum,
	 		cpqRackName,
	 		cpqRackCommonEnclosureName,
			cpqRackNetConnectorName,
			cpqRackNetConnectorLocation,
			agentBscSwFileAddr,
			agentBscSwFile,
			agentBscSwFileLoadType 
		}

		DESCRIPTION
		"The switch has successfully transferred a configuration file."
		
			 --#SEVERITY INFORMATIONAL
			 
	::= 161002


	switchTFTPTransferSucceeded TRAP-TYPE
		ENTERPRISE compaq
		VARIABLES  {
	 		cpqRackUid,
	 		cpqRackCommonEnclosureSerialNum,
	 		cpqRackNetConnectorSerialNum,
	 		cpqRackName,
	 		cpqRackCommonEnclosureName,
			cpqRackNetConnectorName,
			cpqRackNetConnectorLocation,
			agentBscSwFileAddr,
			agentBscSwFile,
			agentBscSwFileLoadType		
		}

		DESCRIPTION
		"The switch has successfully completed a TFTP transfer."
		
			 --#SEVERITY INFORMATIONAL
			 
	::= 161003

	switchTFTPTransferFailed TRAP-TYPE
		ENTERPRISE compaq
		VARIABLES  {
	 		cpqRackUid,
	 		cpqRackCommonEnclosureSerialNum,
	 		cpqRackNetConnectorSerialNum,
	 		cpqRackName,
	 		cpqRackCommonEnclosureName,           
			cpqRackNetConnectorName,
			cpqRackNetConnectorLocation,
			agentBscSwFileAddr,
			agentBscSwFile,
			agentBscSwFileLoadType		
		}

		DESCRIPTION
		"The switch has failed a TFTP transfer."
		
			 --#SEVERITY MINOR
			 
	::= 161004
	
	switchFileInvalid	TRAP-TYPE
		ENTERPRISE compaq
		VARIABLES  {
	 		cpqRackUid,
	 		cpqRackCommonEnclosureSerialNum,
	 		cpqRackNetConnectorSerialNum,
	 		cpqRackName,
	 		cpqRackCommonEnclosureName,           
			cpqRackNetConnectorName,
			cpqRackNetConnectorLocation,
			agentBscSwFileAddr,
			agentBscSwFile,
			agentBscSwFileLoadType,
			agentBscSwFileStatus		
		}

		DESCRIPTION
		"Invalid firmware or configuration image downloaded."
		
		 	--#SEVERITY MINOR
		 
	::= 161005

	switchFanFailed TRAP-TYPE
		ENTERPRISE compaq
		VARIABLES  {
	 		cpqRackUid,
	 		cpqRackCommonEnclosureSerialNum,
	 		cpqRackNetConnectorSerialNum,
	 		cpqRackName,
	 		cpqRackCommonEnclosureName,           
			cpqRackNetConnectorName,
			cpqRackNetConnectorLocation,
			cpqRackNetConnectorSparePartNumber,
			agentSwitchFanIndex,
			agentSwitchFanCondition              			
		}

		DESCRIPTION
		"The switch fan has failed."
			
			 --#SEVERITY CRITICAL
			
	::= 161006

	switchFanOk TRAP-TYPE
		ENTERPRISE compaq
		VARIABLES  {
	 		cpqRackUid,
	 		cpqRackCommonEnclosureSerialNum,
	 		cpqRackNetConnectorSerialNum,
	 		cpqRackName,
	 		cpqRackCommonEnclosureName,           
			cpqRackNetConnectorName,
			cpqRackNetConnectorLocation,
			cpqRackNetConnectorSparePartNumber,
			agentSwitchFanIndex,
			agentSwitchFanCondition              			
		}

		DESCRIPTION
		"The switch fan has returned to normal operation."
		
			 --#SEVERITY INFORMATIONAL
			 
	::= 161007

	switchTempSensorDegraded TRAP-TYPE
		ENTERPRISE compaq
		VARIABLES  {
	 		cpqRackUid,
	 		cpqRackCommonEnclosureSerialNum,
	 		cpqRackNetConnectorSerialNum,
	 		cpqRackName,
	 		cpqRackCommonEnclosureName,           
			cpqRackNetConnectorName,
			cpqRackNetConnectorLocation,
			cpqRackNetConnectorSparePartNumber,
			agentSwitchTempSensorIndex,
			agentSwitchTempSensorCurrent,
        	agentSwitchTempSensorThreshold,
        	agentSwitchTempSensorCondition,
        	agentSwitchTempSensorTempType
		}

		DESCRIPTION
		"The switch temperature sensor indicates a high temperature condidtion."
		
			 --#SEVERITY MAJOR
			 
	::= 161008

	switchTempSensorFailed TRAP-TYPE
		ENTERPRISE compaq
		VARIABLES  {
	 		cpqRackUid,
	 		cpqRackCommonEnclosureSerialNum,
	 		cpqRackNetConnectorSerialNum,
	 		cpqRackName,
	 		cpqRackCommonEnclosureName,           
			cpqRackNetConnectorName,
			cpqRackNetConnectorLocation,
			cpqRackNetConnectorSparePartNumber,
			agentSwitchTempSensorIndex,
			agentSwitchTempSensorCurrent,
        	agentSwitchTempSensorThreshold,
        	agentSwitchTempSensorCondition,
        	agentSwitchTempSensorTempType
		}

		DESCRIPTION
		"The switch temperature sensor indicates an over-temperature condition."
		
			 --#SEVERITY CRITICAL
			 
	::= 161009


	switchTempSensorOk TRAP-TYPE
		ENTERPRISE compaq
		VARIABLES  {
	 		cpqRackUid,
	 		cpqRackCommonEnclosureSerialNum,
	 		cpqRackNetConnectorSerialNum,
	 		cpqRackName,
	 		cpqRackCommonEnclosureName,           
			cpqRackNetConnectorName,
			cpqRackNetConnectorLocation,
			cpqRackNetConnectorSparePartNumber,
			agentSwitchTempSensorIndex,
			agentSwitchTempSensorCurrent,
        	agentSwitchTempSensorThreshold,
        	agentSwitchTempSensorCondition,
        	agentSwitchTempSensorTempType
		}

		DESCRIPTION
		"The switch temperature sensor indicates temperature has returned to normal."
		
			 --#SEVERITY INFORMATIONAL
			 
	::= 161010


-- Switch temperature shall be monitored for high (75°C) and over (80°C) temperature conditions. 
-- Whenever high temperature condition occurs a SNMP notification shall be generated by the switch
-- and sent to the SNMP manager configured. But, whenever over temperature condition occurs a SNMP 
-- notification generated and sent, followed by a shutdown notification from CPU by disabling primary
-- VRM (DC-DC converter). If it falls below 75°C before going over 80°C, switchTempSensorOk notification
-- is generated.

-- High Temperature -> Assert Temperature Degraded Trap
-- Over Temperature -> Assert Temperature Failed Trap -> Disable Primary VRM (DC-DC converter)
-- Normal Temperature -> Assert Temperature Normal Trap


	switchPostSuccess TRAP-TYPE
		ENTERPRISE compaq
		VARIABLES  {
	 		cpqRackUid,
 			cpqRackCommonEnclosureSerialNum,
 			cpqRackNetConnectorSerialNum,
	 		cpqRackName,
	 		cpqRackCommonEnclosureName,           
			cpqRackNetConnectorName,
			cpqRackNetConnectorLocation,
			cpqRackNetConnectorSparePartNumber		
		}

		DESCRIPTION
		"The switch has successfully completed POST."
		
			 --#SEVERITY MINOR
			 
	::= 161011

	switchLoginFailure TRAP-TYPE
		ENTERPRISE compaq
		VARIABLES  {
	 		cpqRackUid,
	 		cpqRackCommonEnclosureSerialNum,
	 		cpqRackNetConnectorSerialNum,
	 		cpqRackName,
	 		cpqRackCommonEnclosureName,           
			cpqRackNetConnectorName,
			cpqRackNetConnectorLocation
		--	switchLoginNameAttempted (if available)
		}

		DESCRIPTION
		"The switch has rejected a login attempt."
		
			 --#SEVERITY MINOR
			 
	::= 161012
	
	switchLocationChange TRAP-TYPE
		ENTERPRISE compaq
		VARIABLES {
			cpqRackUid,
	 		cpqRackCommonEnclosureSerialNum,
	 		cpqRackNetConnectorSerialNum,
	 		cpqRackName,
	 		cpqRackCommonEnclosureName,           
			cpqRackNetConnectorName,
			cpqRackNetConnectorLocation
		}
		
		DESCRIPTION
		"The switch location has changed.  The new
 		 location is defined in the variables. The 
 		 trap will be sent out on the next boot"
 		 	
 		 	 --#SEVERITY INFORMATIONAL
 		 	 
	::= 161013
	
	switchCubeTypeChange TRAP-TYPE
		ENTERPRISE compaq
		VARIABLES  {
	 		cpqRackUid,
	 		cpqRackCommonEnclosureSerialNum,
	 		cpqRackNetConnectorSerialNum,
	 		cpqRackName,
	 		cpqRackCommonEnclosureName,           
			cpqRackNetConnectorName,
			cpqRackNetConnectorLocation,
			cpqRackNetConnectorSparePartNumber,
			agentSwitchCubeType,
    		agentSwitchCubeSpareName,
    		agentSwitchCubeSparePartNumber
		}

		DESCRIPTION
		"Trap for connection different cube type. 
		 Customer has changed the cube type since 
		 the last boot. "
		 
		  --#SEVERITY INFORMATIONAL
		  
	::= 161014
	
	switchSNTPServiceUnavailable 	TRAP-TYPE
		ENTERPRISE compaq
		VARIABLES {
			cpqRackUid,
			cpqRackCommonEnclosureSerialNum,
			cpqRackNetConnectorSerialNum,
			cpqRackName,
			cpqRackCommonEnclosureName,
			cpqRackNetConnectorName,
			cpqRackNetConnectorLocation,
			agentSNTPServer1IPAddr,
			agentSNTPServer2IPAddr
		}
		
		DESCRIPTION
		"A SNTP Server was configured, but no SNTP servers were found.
		
			This trap is sent once if SNTP is enabled,	 a SNTP server 
		 is configured, and a SNTP server could not be contacted for 
		 10 minutes from the start time.  The start time will be defined 
		 as when both SNTP was enabled and a SNTP server was configured 
		 or when a SNTP server was contacted successfully."
		 
		  --#SEVERITY MINOR
		  
	::= 161015

END

--	switchPowerSupplyDegraded TRAP-TYPE
--		ENTERPRISE compaq
--		VARIABLES  {
--	 		cpqRackUid,
--	 		cpqRackCommonEnclosureSerialNum,
--	 		cpqRackNetConnectorSerialNum,
--	 		cpqRackName,
--	 		cpqRackCommonEnclosureName,           
--			cpqRackNetConnectorName,
--			cpqRackNetConnectorLocation,
--			cpqRackNetConnectorSparePartNumber,
--			agentSwitchPowerSupplyMaxPwrOutput,
--       	agentSwitchPowerSupplyCurPwrOutput,
--        	agentSwitchPowerSupplyIntakeTemp,
-- 			agentSwitchPowerSupplyExhaustTemp,
--       	agentSwitchPowerSupplyStatus,
--        	agentSwitchPowerSupplyInputLineStatus,
--       	agentSwitchPowerSupplyCondition			
--		}
--
--		DESCRIPTION
--		"The switch power supply is degraded."
--	::= 161xxx
--
--	switchPowerSupplyFailed TRAP-TYPE
--		ENTERPRISE compaq
--	VARIABLES  {
-- 		cpqRackUid,
-- 		cpqRackCommonEnclosureSerialNum,
-- 		cpqRackNetConnectorSerialNum,
-- 		cpqRackName,
-- 		cpqRackCommonEnclosureName,           
--		cpqRackNetConnectorName,
--		cpqRackNetConnectorLocation,
--		cpqRackNetConnectorSparePartNumber,
--		agentSwitchPowerSupplyMaxPwrOutput,
--    	agentSwitchPowerSupplyCurPwrOutput,
--    	agentSwitchPowerSupplyIntakeTemp,
--		agentSwitchPowerSupplyExhaustTemp,
--    	agentSwitchPowerSupplyStatus,
--    	agentSwitchPowerSupplyInputLineStatus,
--    	agentSwitchPowerSupplyCondition			
--	}
--
--	DESCRIPTION
--	"The switch power supply has failed."
--::= 161xxx
--
--switchPowerSupplyOk TRAP-TYPE
--	ENTERPRISE compaq
--	VARIABLES  {
-- 		cpqRackUid,
-- 		cpqRackCommonEnclosureSerialNum,
-- 		cpqRackNetConnectorSerialNum,
-- 		cpqRackName,
-- 		cpqRackCommonEnclosureName,           
--		cpqRackNetConnectorName,
--		cpqRackNetConnectorLocation,
--		cpqRackNetConnectorSparePartNumber,
--		agentSwitchPowerSupplyMaxPwrOutput,
--    	agentSwitchPowerSupplyCurPwrOutput,
--    	agentSwitchPowerSupplyIntakeTemp,
--		agentSwitchPowerSupplyExhaustTemp,
--    	agentSwitchPowerSupplyStatus,
--    	agentSwitchPowerSupplyInputLineStatus,
--    	agentSwitchPowerSupplyCondition			
--	}
--
--	DESCRIPTION
--	"The switch power supply is normal."
--::= 161xxx

--	switchSafeModeChange TRAP-TYPE
--		ENTERPRISE compaq
--		VARIABLES {
--			cpqRackUid,
--	 		cpqRackCommonEnclosureSerialNum,
--	 		cpqRackNetConnectorSerialNum,
--	 		cpqRackName,
--	 		cpqRackCommonEnclosureName,           
--			cpqRackNetConnectorName,
--			cpqRackNetConnectorLocation,
--			cpqRackNetConnectorSparePartNumber,
--			agentSwitchSafeModeStatus
--		}
		
--		DESCRIPTION
--		"Trap for safe mode change"
--	::= 161xxx
