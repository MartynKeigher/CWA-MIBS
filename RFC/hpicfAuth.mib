--**MOD+***********************************************************************
 -- Module:   hpicfAuth.mib
 --
 -- Copyright (C) 2000-2018 Hewlett Packard Enterprise Development LP
 -- All Rights Reserved.
 --
 -- The contents of this software are proprietary and confidential
 -- to the Hewlett Packard Enterprise Development LP.  No part of this
 -- program may be photocopied, reproduced, or translated into another
 -- programming language without prior written consent of the
 -- Hewlett Packard Enterprise Development LP.
 --
 -- Purpose:  Defining proprietary MIB objects for AUTH.
 --
 --MOD-***********************************************************************/

HP-AUTH-MIB DEFINITIONS ::= BEGIN

    IMPORTS
        OBJECT-TYPE, MODULE-IDENTITY, Integer32, Counter32, IpAddress,
        Gauge32, Unsigned32, TimeTicks, NOTIFICATION-TYPE
             FROM SNMPv2-SMI
        RowStatus, DisplayString, TruthValue, DateAndTime
            FROM SNMPv2-TC
        OBJECT-GROUP, MODULE-COMPLIANCE, NOTIFICATION-GROUP
            FROM SNMPv2-CONF
        hpSwitch
          FROM HP-ICF-OID 
        ospfIfEntry, ospfVirtIfEntry
            FROM OSPF-MIB
        InetAddress, InetAddressType
            FROM INET-ADDRESS-MIB
        rip2IfConfEntry
            FROM RIPv2-MIB;

    hpSwitchAuthenticationMIB MODULE-IDENTITY


        LAST-UPDATED "201901140000Z"  -- Jan 14, 2019
        ORGANIZATION "HPE Networking"
        CONTACT-INFO "Hewlett Packard Company
                      8000 Foothills Blvd.
                      Roseville, CA 95747"

        DESCRIPTION  "This MIB module describes objects for managing
                     the Authentication features of devices in the HP
                     Integrated Communication Facility product line."
 
        REVISION     "201901140000Z"  -- Jan 14, 2019
        DESCRIPTION  "Added  MIB object 'hpSwitchTacacsOrderingSequence' in
                     'hpSwitchTacacsConfig'."

        REVISION     "201811120000Z"  -- Nov 12, 2018
        DESCRIPTION  "Modified the MIB object 'hpSwitchRadiusFqdnRetry' in
                      'hpSwitchRadiusConfig' table."

        REVISION     "201809070000Z"  -- Sep 07, 2018
        DESCRIPTION  "Added ' hpSwitchRadiusFqdnRetry' MIB object 
                      in 'hpSwitchRadiusConfig' table."

        REVISION     "201808060000Z"  -- August 06, 2018
        DESCRIPTION  "Added 'hpSwitchRadiusServerIsClearPass' MIB object 
                      in 'hpSwitchRadiusServerTable' table."

        REVISION     "201807190000Z"  -- Jul 19, 2018
        DESCRIPTION  "Added new MIB object for framed-ip-address
                      hpSwitchRadiusFramedIpv4Address."

        REVISION     "201808060000Z"  -- August 06, 2018
        DESCRIPTION  "Added 'hpSwitchRadiusServerIsClearPass' MIB object 
                      in 'hpSwitchRadiusServerTable' table."

        REVISION     "201807190000Z"  -- Jul 19, 2018
        DESCRIPTION  "Added new MIB object for framed-ip-address
                      hpSwitchRadiusFramedIpv4Address."

        REVISION     "201807180000Z"  -- July 18, 2018
        DESCRIPTION  "Added new MIB objects for NAS-ID for RADIUS group
                      hpSwitchAAAServerGroupNasId."

        REVISION     "201805290000Z"  -- May 29, 2018
        DESCRIPTION  "Changes for TACACS+ inorder to support IPv6
                      Added new MIB objects -
                      hpSwitchTacacsServerAddressType,
                      hpSwitchTacacsServerAddress,
                      hpTacacsStatsTacacsServerAdrType,
                      hpTacacsStatsTacacsServerAddr."

        REVISION     "201804270000Z"  -- April 27, 2018
        DESCRIPTION  "Added new MIB objects for RADIUS tracking
                      hpSwitchRadiusTrackPassEncrypt."

        REVISION     "201802210000Z"  -- Feb 21, 2018
        DESCRIPTION  "Added new object 'hpSwitchAuthConsoleLockout' to
                      'hpSwitchAuthenticationConfig'."

        REVISION     "201801160000Z"  -- Jan 16, 2018
        DESCRIPTION  "Added new MIB objects for RADIUS tracking
                      hpSwitchRadiusTrackingPassword,
                      hpSwitchRadiusTrackDeadOnly,
                      hpSwitchRadiusTrackReqPktCount."
        
        REVISION     "201711220000Z"  -- Nov 22, 2017
        DESCRIPTION  "Added new index 'rest' the object 'hpSwitchAuthenIndex'"

        REVISION     "201807190000Z"  -- Jul 19, 2018
        DESCRIPTION  "Added new MIB object for framed-ip-address
                      hpSwitchRadiusFramedIpv4Address."

        REVISION     "201709280000Z"  -- Sep 28, 2017
        DESCRIPTION  "Added new MIB objects for RADIUS deadtime and tracking
                      hpSwitchRadiusDeadTimeInfinite,
                      hpSwitchRadiusTrackingInterval."
 
        REVISION     "201705250000Z"  -- May 25, 2017
        DESCRIPTION  "Added new MIB objects for front-panel-security commands 
                      hpSwitchFrontPanelSecurityCompliance,
                      hpSwitchFrontPanelSecurityGroup,
                      hpSwitchFpsPasswordClear,
                      hpSwitchFpsFactoryReset,
                      hpSwitchFpsPasswordRecovery,
                      hpSwitchFpsDiagnosticResetClearButton,
                      hpSwitchFpsDiagnosticResetSerialConsole,
                      hpSwitchFpsDisplayInConfig"

        REVISION     "201703160000Z"  -- Mar 16, 2017
        DESCRIPTION  "Added new MIB objects for configuring cppm
                      identity and key which are used during authentication
                      with cppm server -
                      hpSwitchRadiusCppmIdentity,
                      hpSwitchRadiusCppmKey,
                      hpSwitchRadiusCppmEncryptedKey"

        REVISION     "201701190000Z"  -- Jan 19, 2017
        DESCRIPTION  "Added new MIB objects for user-based lockout - 
                      hpSwitchAuthUnlockUser,
                      hpSwitchAuthUserBasedLockout."

        REVISION     "201611210000Z"  -- Nov 21, 2016
        DESCRIPTION  "Added new MIB object hpSwitchAuthenHideSensitiveData."

        REVISION     "201611110000Z"  -- Nov 11, 2016
        DESCRIPTION  "Added new MIB objects for encrypted key-
                      hpSwitchOspfVirtIfAuthKeyEncrypted,
                      hpSwitchOspfIfAuthKeyEncrypted and
                      hpSwitchRip2IfConfAuthKeyEncrypted."
       
        REVISION     "201607290000Z"  -- Jul 29, 2016
        DESCRIPTION  "Added new MIB objects for non-plaintext-sha256 command-
                      hpicfSwitchNonPlaintextSha256,
                      hpicfSwitchUserPasswordHashSha256,
                      hpicfSwitchOperatorPasswordHashSha256,
                      hpSwitchLocalMgmtPrivUsernamePasswdSha256,
                      and modified following MIB object for sha256 support -
                      hpicfSwitchUserPasswordHashType,
                      hpicfSwitchOperatorPasswordHashType,
                      hpSwitchLocalMgmtPrivUsernamePasswdType under new config groups
                      hpSwitchUserConfigGroup3,
                      hpSwitchAuthLocalMgmtPrivUserGroup3 and new compliance
                      hpSwitchUserConfigMIBCompliance3,
                      hpSwitchLocalMgmtPrivUserMIBCompliance3 And deprecated -
                      hpSwitchUserConfigGroup2,
                      hpSwitchAuthLocalMgmtPrivUserGroup2 and
                      hpSwitchUserConfigMIBCompliance2,
                      hpSwitchLocalMgmtPrivUserMIBCompliance2"

        REVISION     "201606270000Z"  -- Jun 27, 2016
        DESCRIPTION  "Added new MIB objects for SSH Client authentication 
                      hpSwitchAuthenClientPrimary and
                      hpSwitchAuthenClientSecondary."

        REVISION     "201602230000Z"  -- Feb 23, 2016
        DESCRIPTION  "Added new MIB objects for CAC authentication - public key -
                      hpSwitchAuthenLoginTwoFactorType,
                      hpSwitchAuthenEnableTwoFactorType,
                      hpSwitchAuthenLoginSecondAuthMethod and
                      hpSwitchAuthenEnableSecondAuthMethod under new config group
                      hpSwitchAuthenticationConfigGroup5 and new compilance
                      hpSwitchAuthenticationMIBCompliance12. And deprecated -
                      hpSwitchAuthenticationConfigGroup3 and
                      hpSwitchAuthenticationMIBCompliance11"

        REVISION     "201601220000Z"  -- Jan 22, 2016
        DESCRIPTION  "Added new MIB object for timeWindow type -
                      hpSwitchRadiusServerDynAutzTimeWindowType under new
                      config group hpSwitchRadiusConfigGroup4 and new 
                      compliance hpSwitchAuthenticationMIBCompliance11"

        REVISION     "201510280000Z"  -- Oct 28, 2015
        DESCRIPTION  "Modified following MIB objects for password complexity -
                      hpicfSwitchUserPwdAgingInterval,
                      hpicfSwitchOperatorPwdAgingInterval,
                      hpSwitchLocalMgmtPwdUserAgingInterval"


        REVISION     "201507020000Z"  -- July 02, 2015
        DESCRIPTION  "Added hpSwitchAuthNotifications object."

        REVISION     "201505240000Z"  -- May 26, 2015
        DESCRIPTION  "Added hpSwitchAuthenticationPasswordConfigGroup"

        
        REVISION     "201504010000Z"  -- April 01, 2015
        DESCRIPTION  "Added following MIB objects and object group for RIP authentication
                      table -
                      hpSwitchRipIfAuthTable,
                      hpSwitchRipIfAuthEntry,
                      hpSwitchRipIfAuthChain,
                      hpSwitchRipAuthGroup"

        REVISION     "201503160000Z"  -- March 16, 2015
        DESCRIPTION  "Added x509Certificate option under hpSwitchAuthenLoginPrimary object
                      and x509Certificate option under hpSwitchAuthenEnablePrimary object"

        REVISION     "201408040000Z"  -- August 04, 2014
        DESCRIPTION  "Added stats objects for TACACS+, updated
                     description"

        REVISION     "201403120000Z"  -- Mar 12, 2014
        DESCRIPTION  "Added hpSwitchAuthAllowVlanTagged"

        REVISION     "201311120000Z"  -- Nov 12, 2013
        DESCRIPTION  "Added hpicfSwitchBypassUsername"
        
        REVISION     "201306120000Z"  -- June 12, 2013
        DESCRIPTION  "Deprecated object
                     hpSwitchRadiusServerIpAddr and compliances
                     hpSwitchUserConfigMIBCompliance,
                     hpSwitchAuthenticationMIBCompliance3,
                     hpSwitchAuthenticationMIBCompliance5,
                     hpSwitchAuthenticationMIBCompliance4,
                     hpSwitchAuthenticationMIBComplianceOobm.
                     Added objects hpSwitchRadiusServerAddrType,
                     hpSwitchRadiusServerAddress,hpSwitchAuthLockoutDelay.
                     Added compliances
                     hpSwitchAuthenticationMIBComplianceOobm1,
                     hpSwitchAuthenticationMIBCompliance6.Added
                     groups hpSwitchAuthenticationConfigGroup2,
                     hpSwitchRadiusConfigGroup2."

        REVISION     "201305270000Z"  -- May 27, 2013
        DESCRIPTION  "Added 'hpSwitchMinimumPasswordLength',
                      'hpSwitchAuthenticationConfigGroup3',
                      'hpSwitchAuthenticationMIBCompliance7'
                      and deprecated 
                      'hpSwitchAuthenticationConfigGroup2'
                      'hpSwitchAuthenticationMIBCompliance6'."

        REVISION     "201205110000Z"  -- May 11, 2012
        DESCRIPTION  "Added hpSwitchRadiusServerAddrType,
                      hpSwitchRadiusServerAddress"

        REVISION     "201205010000Z"  -- May 1, 2012
        DESCRIPTION  "Added hpSwitchAuthLockoutDelay."

        REVISION     "201106020000Z"  -- June 2, 2011
        DESCRIPTION  "Added 'hpSwitchServerNewCertKeySizeExists'"

        REVISION     "201102120000Z"  -- February 12, 2011
        DESCRIPTION  "Added hpSwitchAuthenticationEncryptCredentialsMethod,
                      hpSwitchTacacsAuthKeyEncrypted,
                      hpSwitchTacacsServerKeyEncrypted,
                      hpSwitchRadiusAuthKeyEncrypted,
                      hpSwitchRadiusServerKeyEncrypted,
                      hpSwitchKmsKeyEncrypted,
                      hpicfSwitchUserPasswordEncrypted,
                      hpicfSwitchOperatorPasswordEncrypted,
                      hpicfSwitchPortAccessPasswordEncrypted."

        REVISION     "201102070000Z"  -- February 07, 2011
        DESCRIPTION  "Added hpSwitchLocalMgmtPrivUsernamesTable."

        REVISION     "200906060000Z"  -- June 6, 2009
        DESCRIPTION  "Added hpicfSwitchPortAccessName, 
                      hpicfSwitchPortAccessPassword,
                      hpicfSwitchUserPasswordHashType, 
                      hpicfOperatorPasswordHashType, 
                      hpicfPortAccessPasswordHashType."

        REVISION     "200906030000Z"  -- June 3, 2009
        DESCRIPTION  "Added larger SIZE parameters, added notes to
                      refer to product documentation and removed
                      restriction on space character to comments for
                      hpicfSwitchUserName, hpicfSwitchOperatorName,
                      hpicfSwitchUserPassword, hpicfSwitchOperatorPassword"

        REVISION     "200904020000Z"  -- April 2, 2009
        DESCRIPTION  "Removed SIZE parameters from UserName, OperatorName,
                      UserPassword, OperatorPassword"

        REVISION     "200902270000Z"  -- February 27, 2009
        DESCRIPTION  "Added cachedReauth to  
                      'hpSwitchAuthenLoginSecondary' values."

        REVISION     "200901290000Z"  -- January 29, 2009
        DESCRIPTION  "Added 'hpSwitchTacacsServerIsOobm' MIB object 
                      in 'hpSwitchTacacsServersTable' table and
                      'hpSwitchRadiusServerIsOobm' MIB object
                      in 'hpSwitchRadiusServerTable' table."

        REVISION     "200807110000Z"  -- July 11, 2008
        DESCRIPTION  "Added 'hpSwitchAuthenLoginServerGroupName',
                     'hpSwitchAuthenEnableServerGroupName' MIB objects.
                      Added hpSwitchAAAServerGroupTable."

        REVISION     "200806110000Z"  -- June 11, 2008
        DESCRIPTION  "Added radiusPeapMSChapv2 to                       
                     'hpSwitchAuthenEnablePrimary' values."

        REVISION     "200709210000Z"  -- September 21, 2007
        DESCRIPTION  "Added 'hpSwitchRadiusDynAutzPortNumber',
                     'hpSwitchRadiusServerDynAutzEnabled',
                     'hpSwitchRadiusServerDynAutzTimeWindow' MIB objects.
                     'hpSwitchRadiusAuthPortNumber' MIB object renamed to
                     'hpSwitchRadiusServerAuthPortNumber',
                     'hpSwitchRadiusAcctPortNumber' MIB object renamed to
                     'hpSwitchRadiusServerAcctPortNumber'."

        REVISION     "200610050000Z"  -- October 5, 2006
        DESCRIPTION  "Added 'hpicfSwitchUserConfigTable' MIB object."

        REVISION     "200409120000Z"  -- September 12, 2004
        DESCRIPTION  "Moved 802.1x objects to separate module."

        REVISION     "200403310012Z"  -- March 31, 2004
        DESCRIPTION  "Revised version of this MIB module."

        REVISION     "200108100238Z"  -- August 10, 2001
        DESCRIPTION  "Initial version of this MIB module."

        REVISION     "201808060000Z"  -- August 06, 2018
        DESCRIPTION  "Added 'hpSwitchRadiusServerIsClearPass' MIB object 
                      in 'hpSwitchRadiusServerTable' table."
     
        ::= { hpSwitch 16 }
            
-- ------------------------------------------------------------
    -- Configuration support for Authentication
-- ------------------------------------------------------------

    hpSwitchAuthenticationConfig
        OBJECT IDENTIFIER ::= { hpSwitchAuthenticationMIB 1 }

    hpSwitchNumLoginAttempts OBJECT-TYPE
        SYNTAX      Integer32 (1..10)
        MAX-ACCESS  read-write
        STATUS      current
        DESCRIPTION "The number of login attempts allowed, both per session
                     and within the time of hpSwitchAuthLockoutDelay."
        DEFVAL      { 3 }
        ::= { hpSwitchAuthenticationConfig 1 }

    hpSwitchAuthRespectPriv OBJECT-TYPE
        SYNTAX      INTEGER {
                        disabled(1),
                        enabled(2)
                    }
        MAX-ACCESS  read-write
        STATUS      current
        DESCRIPTION "This object allows the switch to set privilege level
                     of the session based on the received configuration
                     variable from the authentication server. For RADIUS, the
                     Service-Type attribute's configured value on the server
                     should be 6-Administrative for manager's privilege level,
                     or 7-NAS-prompt for the user/operator privilege level."
        DEFVAL    {1}
        ::= { hpSwitchAuthenticationConfig 2 }

    hpSwitchAuthenticationEncryptCredentialsMethod OBJECT-TYPE
        SYNTAX      INTEGER {
                        none (0),
                        aes256cbc (1)
                    }
        MAX-ACCESS  read-write
        STATUS      current
        DESCRIPTION "This object determines the methods used to encrypt
                    passwords configured on this device."
        DEFVAL      { 0 }
        ::= { hpSwitchAuthenticationConfig 3 }

    hpSwitchAuthLockoutDelay OBJECT-TYPE
        SYNTAX      Integer32 (0..3600)
        MAX-ACCESS  read-write
        STATUS      current
        DESCRIPTION "The number of seconds after repeated login failures
                     before a user may again attempt login, and the period
                     within which login rate is limited. When the value is set 0,
                     the login rate limit feature is disabled."
        DEFVAL      { 0 }
        ::= { hpSwitchAuthenticationConfig 4 }
		
	hpSwitchMinimumPasswordLength OBJECT-TYPE
        SYNTAX      Integer32 (0..1024)
        MAX-ACCESS  read-write
        STATUS      current
        DESCRIPTION "Minimum number of permissible characters required
                     to set a new password for manager, operator, or
                     local management privilege user. The exact range
                     of valid values for this object is implementation
                     dependent; consult the product documentation to
                     determine the supported range for a specific
                     product."
        ::= { hpSwitchAuthenticationConfig 5 }

    hpSwitchAuthAllowVlanTagged OBJECT-TYPE
        SYNTAX      TruthValue
        MAX-ACCESS  read-write
        STATUS      current
        DESCRIPTION "When set to 'true', tagged VLAN membership changes
		     are immediately applied on AAA enabled ports.
		     By default, VLAN changes are postponed when there
		     are authenticated clients connected on the port."
        DEFVAL      {false}
        ::= { hpSwitchAuthenticationConfig 6 }

    hpSwitchAuthenHideSensitiveData OBJECT-TYPE
        SYNTAX      INTEGER {
                        enable   (1),
                        disable  (2)
                    }
        MAX-ACCESS  read-write
        STATUS      current
        DESCRIPTION "This object enables/disables hiding of the sensitive
                     data in standard secure-mode."

        DEFVAL      { 2 }
        ::= { hpSwitchAuthenticationConfig 7 }

   hpSwitchAuthUnlockUser OBJECT-TYPE
        SYNTAX      OCTET STRING (SIZE(0..1024))
        MAX-ACCESS  read-write
        STATUS      current
        DESCRIPTION "The User Name, in ASCII format. The exact size of this
                     object is implementation dependent; the user will be
                     unlocked, if the current state of the user is locked       
                     out."
        ::= { hpSwitchAuthenticationConfig 8 }

   hpSwitchAuthUserBasedLockout OBJECT-TYPE
        SYNTAX      INTEGER {
                        enable   (1),
                        disable  (2)
                    }
        MAX-ACCESS  read-write
        STATUS      current
        DESCRIPTION "This object enables/disables the user-based-lockout.
                     If this feature is enabled, the lockout is based on
                     username and not based on the IP address."
        DEFVAL      { 2 }

        ::= { hpSwitchAuthenticationConfig 9 }

   hpSwitchAuthConsoleLockout OBJECT-TYPE
        SYNTAX      INTEGER {
                        enable   (1),
                        disable  (2)
                    }
        MAX-ACCESS  read-write
        STATUS      current
        DESCRIPTION "This object enables/disables the console-based-lockout
                     feature. With this, we can have username based lockout
                     for console."
        DEFVAL      { disable }

        ::= { hpSwitchAuthenticationConfig 10 }

-- ------------------------------------------------------------
    -- Configuration support for Authentication
-- ------------------------------------------------------------
 
    hpSwitchAuthenticationPasswordConfig 
        OBJECT IDENTIFIER ::= { hpSwitchAuthenticationMIB 25 }

    hpSwitchAuthPwdControlCheck OBJECT-TYPE
        SYNTAX      INTEGER{
                       enable(1),
                       disable(2)
                   }
        MAX-ACCESS  read-write
        STATUS      current
        DESCRIPTION "This object enables the password configuration feature."
        DEFVAL      {disable}
        ::= { hpSwitchAuthenticationPasswordConfig 1 }

    hpSwitchAuthPwdUserNameCheck OBJECT-TYPE
        SYNTAX      INTEGER{
                       enable(1),
                       disable(2)
                   }
        MAX-ACCESS  read-write
        STATUS      current
        DESCRIPTION "This object enables the check to ensure that the password
                     does not contain repeat or reverse characters of the
                     associated username."
        DEFVAL      {disable}
        ::= { hpSwitchAuthenticationPasswordConfig 2 }

    hpSwitchAuthPwdRepeatCharactersCheck OBJECT-TYPE
        SYNTAX      INTEGER{
                       enable(1),
                       disable(2)
                   }
        MAX-ACCESS  read-write
        STATUS      current
        DESCRIPTION "This object enables the check that the password does 
                     not contain at least three of the same characters used
                     consecutively."
        DEFVAL      {disable}
        ::= { hpSwitchAuthenticationPasswordConfig 3 }

    hpSwitchAuthPwdRepeatPasswordCheck OBJECT-TYPE
        SYNTAX      INTEGER{
                       enable(1),
                       disable(2)
                   }
        MAX-ACCESS  read-write
        STATUS      current
        DESCRIPTION "This object enables the check that the new password differs         
                     from the previous password by at least four characters."
        DEFVAL      {disable}
        ::= { hpSwitchAuthenticationPasswordConfig 4 }

    hpSwitchAuthPwdAgingCheck OBJECT-TYPE
        SYNTAX      INTEGER{
                       enable(1),
                       disable(2)
                   }
        MAX-ACCESS  read-write
        STATUS      current
        DESCRIPTION "This object enables the check for the password expiry check."
        DEFVAL      {disable}
        ::= { hpSwitchAuthenticationPasswordConfig 5 }

    hpSwitchAuthPwdLogonDetailsCheck OBJECT-TYPE
        SYNTAX      INTEGER{
                       enable(1),
                       disable(2)
                   }
        MAX-ACCESS  read-write
        STATUS      current
        DESCRIPTION "This object enables the previous login details."
        DEFVAL      {enable}
        ::= { hpSwitchAuthenticationPasswordConfig 6 }

    hpSwitchAuthPwdAgingValue OBJECT-TYPE
        SYNTAX      Integer32 (1..365)
                 
        MAX-ACCESS  read-write
        STATUS      current
        DESCRIPTION "This object provides the global aging value."
        DEFVAL      {90}
        ::= { hpSwitchAuthenticationPasswordConfig 7 }

    hpSwitchAuthPwdHistoryCheck OBJECT-TYPE
        SYNTAX      INTEGER{
                       enable(1),
                       disable(2)
                   }
        MAX-ACCESS  read-write
        STATUS      current
        DESCRIPTION "This object enables the password history check."
        DEFVAL      {disable}
        ::= { hpSwitchAuthenticationPasswordConfig 8 }

    hpSwitchAuthPwdHistoryRecordsRange OBJECT-TYPE
        SYNTAX      Integer32 (2..15)
                 
        MAX-ACCESS  read-write
        STATUS      current
        DESCRIPTION "This object indicates the number of password history records."
        DEFVAL      {8}
        ::= { hpSwitchAuthenticationPasswordConfig 9 }

    hpSwitchAuthPwdAlertBeforeExpiry OBJECT-TYPE
        SYNTAX      Integer32 (1..30)
        MAX-ACCESS  read-write
        STATUS      current
        DESCRIPTION "This object indicates the period, in days, by 
                     which the user needs to be alerted before the password expiry."
        DEFVAL      {7}
        ::= { hpSwitchAuthenticationPasswordConfig 10 }

    hpSwitchAuthPwdExpiredUserLoginDays OBJECT-TYPE
        SYNTAX      Integer32 (1..90)
        MAX-ACCESS  read-write
        STATUS      current
        DESCRIPTION "This object indicates the period, in days, 
                     for which the user will be allowed to login after
                     password expiry."
        DEFVAL      {30}
        ::= { hpSwitchAuthenticationPasswordConfig 11 }

    hpSwitchAuthPwdExpiredUserLoginAttempts OBJECT-TYPE
        SYNTAX      Integer32 (1..10)
        MAX-ACCESS  read-write
        STATUS      current
        DESCRIPTION "This object indicates the number of times the user will 
                     be allowed to login to the switch after the expiry 
                     of the password."
        DEFVAL      {3}
        ::= { hpSwitchAuthenticationPasswordConfig 12 }

    hpSwitchAuthPwdUpdateInterval OBJECT-TYPE
        SYNTAX      Integer32 (0..168)
        MAX-ACCESS  read-write
        STATUS      current
        DESCRIPTION "This object indicates the minimum time, in hours, before 
                     which the user is not allowed to change the password."
        DEFVAL      {24}
        ::= { hpSwitchAuthenticationPasswordConfig 13 }
    

    hpSwitchAuthenTable OBJECT-TYPE
        SYNTAX      SEQUENCE OF HpSwitchAuthenEntry
        MAX-ACCESS  not-accessible
        STATUS      current
        DESCRIPTION "This table lists the authentication methods to be
                    tried for granting different access levels through
                    various access tasks."
        ::= { hpSwitchAuthenticationMIB 2 }

    hpSwitchAuthenEntry OBJECT-TYPE 
        SYNTAX      HpSwitchAuthenEntry
        MAX-ACCESS  not-accessible
        STATUS      current
        DESCRIPTION "An Authentication Method Table Entry."
        INDEX       { hpSwitchAuthenIndex }
        ::= {hpSwitchAuthenTable 1}

    HpSwitchAuthenEntry ::=
        SEQUENCE {
            hpSwitchAuthenIndex                  INTEGER,
            hpSwitchAuthenLoginPrimary           INTEGER,
            hpSwitchAuthenLoginSecondary         INTEGER,
            hpSwitchAuthenEnablePrimary          INTEGER,
            hpSwitchAuthenEnableSecondary        INTEGER,
            hpSwitchAuthenLoginServerGroupName   DisplayString,
            hpSwitchAuthenEnableServerGroupName  DisplayString,
            hpSwitchAuthenLoginTwoFactorType      INTEGER,
            hpSwitchAuthenEnableTwoFactorType     INTEGER,
            hpSwitchAuthenLoginSecondAuthMethod   INTEGER,
            hpSwitchAuthenEnableSecondAuthMethod  INTEGER,
            hpSwitchAuthenClientPrimary          INTEGER,
            hpSwitchAuthenClientSecondary        INTEGER,
            hpSwitchAuthenCachedReauthAuthorized TruthValue
        }

    hpSwitchAuthenIndex OBJECT-TYPE
        SYNTAX      INTEGER {
                        console(1),
                        telnet(2),
                        ieee8021X(3),
                        webui(4),
                        ssh(5),
                        webauth(6),
                        macauth(7),
                        snmp(8),
                        localMacAuth(9),
                        rest(10)
                    }
        MAX-ACCESS  not-accessible
        STATUS      current
        DESCRIPTION "Signifies the access task for which authentication
                    methods are listed in this entry."
        ::= {hpSwitchAuthenEntry 1}

    hpSwitchAuthenLoginPrimary OBJECT-TYPE
        SYNTAX      INTEGER {
                        local(1),
                        tacacs(2),
                        radius(3),
                        radiusEap(4),
                        radiusChap(5),
                        sshRsa(6),
                        radiusPeapMSChapv2(7),
                        x509Certificate(8),
                        twoFactor(9),
                        radiusPap(10)
                    }
        MAX-ACCESS  read-write
        STATUS      current
        DESCRIPTION "The value of this object indicates the primary login 
                     authentication mechanism. When a user logs in, the 
                     authentication method configured by this object will 
                     be tried first."
        ::= { hpSwitchAuthenEntry 2 }

    hpSwitchAuthenLoginSecondary OBJECT-TYPE
        SYNTAX      INTEGER {
                        local(1),
                        none(2),
                        authorized(3),
                        cachedReauth(4) 
                    }
        MAX-ACCESS  read-write
        STATUS      current
        DESCRIPTION "The value of this object indicates the secondary 
                     login authentication mechanism, i.e whether Local
                     or Authorized will be tried in case the primary 
                     authentication results in an error.The Local authentication 
                     method uses the credential database on the switch.  
                     The Authorized authentication method will be granted access 
                     without authenticating. The cachedReauth authentication method 
                     will grant access in case of reauthentication retaining the 
                     current session attributes."
        ::= { hpSwitchAuthenEntry 3 }

    hpSwitchAuthenEnablePrimary OBJECT-TYPE
        SYNTAX      INTEGER {
                        local(1),
                        tacacs(2),
                        radius(3),
                        sshPubkey(6),
                        radiusPeapMSChapv2(7),
                        x509Certificate(8),
                        twoFactor(9),
                        radiusPap(10)
                    }
        MAX-ACCESS  read-write
        STATUS      current
        DESCRIPTION "This object configures the primary authentication mechanism
                    that will be tried first when a user requests manager-level access"
        ::= { hpSwitchAuthenEntry 4 }

    hpSwitchAuthenEnableSecondary OBJECT-TYPE
        SYNTAX      INTEGER {
                        local(1),
                        none(2),
                        authorized(3)
                    }
        MAX-ACCESS  read-write
        STATUS      current
        DESCRIPTION "This object indicates the secondary login authentication
                    mechanism, i.e whether Local or Authorized will be tried
                    in case the primary authentication results in an error.
                    The authentication method Local uses the credential
                    database on the switch. The Authorized authentication
                    method will be granted access without authenticating."
        ::= { hpSwitchAuthenEntry 5 }

    hpSwitchAuthenLoginServerGroupName OBJECT-TYPE
        SYNTAX      DisplayString (SIZE(0..255))
        MAX-ACCESS  read-write
        STATUS      current
        DESCRIPTION "The name that defines the RADIUS server group that this
                     authentication method is associated with. The
                     current maximum length is 12."
        ::= { hpSwitchAuthenEntry 6 }

    hpSwitchAuthenEnableServerGroupName OBJECT-TYPE
        SYNTAX      DisplayString (SIZE(0..255))
        MAX-ACCESS  read-write
        STATUS      current
        DESCRIPTION "The name that defines the RADIUS server group that this
                     authentication method is associated with. The
                     current maximum length is 12."
        ::= { hpSwitchAuthenEntry 7 }


   hpSwitchAuthenLoginTwoFactorType OBJECT-TYPE
        SYNTAX      INTEGER {
                        publickeypassword(1),
                        certificatepassword(2)
                    }
        MAX-ACCESS  read-write
        STATUS      current
        DESCRIPTION "This object configures the type of two-factor authentication"
        ::= { hpSwitchAuthenEntry 8 }

    hpSwitchAuthenEnableTwoFactorType OBJECT-TYPE
        SYNTAX      INTEGER {
                        publickeypassword(1),
                        certificatepassword(2)
                    }
        MAX-ACCESS  read-write
        STATUS      current
        DESCRIPTION "This object configures the type of two-factor authentication"
        ::= { hpSwitchAuthenEntry 9 }

   hpSwitchAuthenLoginSecondAuthMethod OBJECT-TYPE
        SYNTAX      INTEGER {
                        local(1),
                        tacacs(2),
                        radius(3)
                    }
        MAX-ACCESS  read-write
        STATUS      current
        DESCRIPTION "This object configures the password configuration
                     for two-factor authentication"
        ::= { hpSwitchAuthenEntry 10 }

    hpSwitchAuthenEnableSecondAuthMethod OBJECT-TYPE
        SYNTAX      INTEGER {
                        local(1),
                        tacacs(2),
                        radius(3)
                    }
        MAX-ACCESS  read-write
        STATUS      current
        DESCRIPTION "This object configures the password configuration
                     for two-factor authentication"
        ::= { hpSwitchAuthenEntry 11 }

    hpSwitchAuthenClientPrimary OBJECT-TYPE
        SYNTAX      INTEGER {
                        x509Certificate(1),
                        none(2)
                    }
        MAX-ACCESS  read-write
        STATUS      current
        DESCRIPTION "This object configures the primary authentication 
                     for SSH when the switch acts as a client."
        ::= { hpSwitchAuthenEntry 12 }

    hpSwitchAuthenClientSecondary OBJECT-TYPE
        SYNTAX      INTEGER {
                        none(1)
                    }
        MAX-ACCESS  read-write
        STATUS      current
        DESCRIPTION "This object indicates the secondary login authentication
                     for SSH when the switch acts as a client.
                     This is a placeholder as secondary authentication
                     is not currently supported when primary authentication
                     is 'certificate' for SSH client."
        ::= { hpSwitchAuthenEntry 13 }

    hpSwitchAuthenCachedReauthAuthorized OBJECT-TYPE
        SYNTAX      TruthValue
        MAX-ACCESS  read-write
        STATUS      current
		              
        DESCRIPTION "When the value of object hpSwitchAuthenLoginSecondary 
                     is set to cachedReauth(4),the ture value set for this 
	             object indicates cachedReauth authentication method will 
		     grant access in case of reauthentication fails."
        ::= { hpSwitchAuthenEntry 14 }



-- ------------------------------------------------------------
    -- Password composition support
-- ------------------------------------------------------------
 
   hpSwitchAuthenPwdCompositionTable OBJECT-TYPE
        SYNTAX      SEQUENCE OF HpSwitchAuthenPwdCompositionEntry
        MAX-ACCESS  not-accessible
        STATUS      current
        DESCRIPTION "This table lists different type of
                     charaters required to create a password 
                     as per UCR guidelines. "
        ::= { hpSwitchAuthenticationMIB 24 }
 
   hpSwitchAuthenPwdCompositionEntry OBJECT-TYPE
        SYNTAX      HpSwitchAuthenPwdCompositionEntry
        MAX-ACCESS  not-accessible
        STATUS      current
        DESCRIPTION "An Authentication Method Table Entry."
        INDEX       { hpSwitchAuthenCompositionIndex}
        ::= {hpSwitchAuthenPwdCompositionTable 1}

    HpSwitchAuthenPwdCompositionEntry ::=
        SEQUENCE {
           hpSwitchAuthenCompositionIndex       INTEGER,
            hpSwitchAuthenCompositionValue       Integer32
        }

    hpSwitchAuthenCompositionIndex OBJECT-TYPE
        SYNTAX      INTEGER {
                       lowerCase(1),
                       upperCase(2),
                       specialCharacter(3),
                       number(4)
                    }
        MAX-ACCESS  not-accessible
        STATUS      current
        DESCRIPTION "This object indicates the different types
                     of charaters required to create a password."
        ::= {hpSwitchAuthenPwdCompositionEntry 1}

    hpSwitchAuthenCompositionValue OBJECT-TYPE
        SYNTAX      Integer32 (2..15)
        MAX-ACCESS  read-write
        STATUS      current
        DESCRIPTION "This object indicates number of characters 
                     allow for password compostion "
                  
        ::= {hpSwitchAuthenPwdCompositionEntry 2}

-- ------------------------------------------------------------
   -- Configuration support for TACACS+ Protocol
-- ------------------------------------------------------------

    hpSwitchTacacsConfig 
        OBJECT IDENTIFIER ::= { hpSwitchAuthenticationMIB 3 }

    hpSwitchTacacsTimeout OBJECT-TYPE
        SYNTAX      Integer32 (1..255)
        MAX-ACCESS  read-write
        STATUS      current
        DESCRIPTION "The duration in seconds to wait for a response from 
                    the TACACS+ server host."
        DEFVAL { 5 }
        ::= { hpSwitchTacacsConfig 1 }

    hpSwitchTacacsAuthKey OBJECT-TYPE
        SYNTAX      OCTET STRING (SIZE(0..100))
        MAX-ACCESS  read-write
        STATUS      current
        DESCRIPTION "The key used in encrypting the packets passed between
                    the TACACS+ server and the client. This key must match
                    the one configured on the server."
        ::= { hpSwitchTacacsConfig 2 }

    hpSwitchTacacsAuthKeyEncrypted OBJECT-TYPE
        SYNTAX      OCTET STRING (SIZE(0..256))
        MAX-ACCESS  read-write
        STATUS      current
        DESCRIPTION "An encrypted form of the key used in encrypting the
                    packets passed between the TACACS+ server and the client.
                    This key must match the one configured on the server.
                    This object may only be read or written when
                    hpSwitchAuthenticationEncryptCredentialsMethod is set to a
                    value other than none(0). At most one of
                    hpSwitchTacacsAuthKey and hpSwitchTacacsAuthKeyEncrypted
                    may be set in any transaction. This object should only be
                    written with an encrypted key previously read from a
                    compatible HP Networking device."
        ::= { hpSwitchTacacsConfig 3 }

    hpSwitchTacacsDeadTime OBJECT-TYPE
        SYNTAX      Integer32 (0..1440)
        MAX-ACCESS  read-write
        STATUS      current
        DESCRIPTION "This object specifies the TACACS+ server unavailability time.
                     When a response is not received from a TACACS+ server, that 
                     server is then not contacted for Authentication, Authorization, 
                     or Accounting (AAA) requests for a period of dead-time defined. 
                     During this period, any AAA request received from the client is 
                     sent to the next available server.  A value of zero indicates 
                     that all AAA requests are continuously sent to the unavailable
                     server."
        DEFVAL { 0 }
        ::= { hpSwitchTacacsConfig 4 }
    
    hpSwitchTacacsOrderingSequence OBJECT-TYPE
        SYNTAX      TruthValue
        MAX-ACCESS  read-write
        STATUS      current
        DESCRIPTION "When this object is set to true, reordering of TACACS+ servers 
                     takes place upon deletion of an existing server, such that further
                     addition of a new TACACS+ server will take place at a lower 
                     priority than the pre-existing servers."
        DEFVAL { false }
        ::= { hpSwitchTacacsConfig 5 }  

    hpSwitchTacacsServersTable OBJECT-TYPE
        SYNTAX      SEQUENCE OF HpSwitchTacacsServersEntry
        MAX-ACCESS  not-accessible
        STATUS      current
        DESCRIPTION "This table lists a maximum of 3 TACACS+ servers."
        ::= { hpSwitchAuthenticationMIB 4 }

    hpSwitchTacacsServersEntry OBJECT-TYPE
        SYNTAX      HpSwitchTacacsServersEntry
        MAX-ACCESS  not-accessible
        STATUS      current
        DESCRIPTION "A TACACS+ server table entry."
        INDEX       { hpSwitchTacacsServerIndex }
        ::= { hpSwitchTacacsServersTable 1 }

    HpSwitchTacacsServersEntry ::=
        SEQUENCE {
            hpSwitchTacacsServerIndex         Integer32,
            hpSwitchTacacsServerIpAddr        IpAddress,
            hpSwitchTacacsServerKey           OCTET STRING,
            hpSwitchTacacsServerStatus        RowStatus,
            hpSwitchTacacsServerIsOobm        TruthValue,
            hpSwitchTacacsServerKeyEncrypted  OCTET STRING,
            hpSwitchTacacsServerAddressType   InetAddressType,
            hpSwitchTacacsServerAddress       InetAddress
        }

    hpSwitchTacacsServerIndex OBJECT-TYPE
        SYNTAX      Integer32 (1..65535)
        MAX-ACCESS  not-accessible
        STATUS      current
        DESCRIPTION "The index value which uniquely identifies a row in
                    the TACACS+ Servers Table."
        ::= { hpSwitchTacacsServersEntry 1 }

    hpSwitchTacacsServerIpAddr OBJECT-TYPE
        SYNTAX      IpAddress
        MAX-ACCESS  read-create
        STATUS      current
        DESCRIPTION "The IP address of a TACACS+ Server."
        ::= { hpSwitchTacacsServersEntry 2 }

    hpSwitchTacacsServerKey OBJECT-TYPE
        SYNTAX      OCTET STRING (SIZE(0..100))
        MAX-ACCESS  read-create
        STATUS      current
        DESCRIPTION "The key used in encrypting the packets passed between
                    the TACACS+ server and the client. This key must match
                    the one configured on the server."
        ::= { hpSwitchTacacsServersEntry 3 }

    hpSwitchTacacsServerStatus OBJECT-TYPE
        SYNTAX      RowStatus
        MAX-ACCESS  read-create
        STATUS      current
        DESCRIPTION "Status of Servers Table row."
        ::= { hpSwitchTacacsServersEntry 4 }

    hpSwitchTacacsServerIsOobm OBJECT-TYPE
        SYNTAX      TruthValue
        MAX-ACCESS  read-create
        STATUS      current
        DESCRIPTION "This object indicates whether this TACACS+ Server
                    is reachable over OOBM (Out Of Band Management) 
                    interface or not. This mib object will be applicable
                    only if there is a physical OOBM port on the device."
       DEFVAL      {false}
        ::= { hpSwitchTacacsServersEntry 5 }

    hpSwitchTacacsServerKeyEncrypted OBJECT-TYPE
        SYNTAX      OCTET STRING (SIZE(0..256))
        MAX-ACCESS  read-create
        STATUS      current
        DESCRIPTION "An encrypted form of the key used in encrypting the
                    packets passed between the TACACS+ server and the client.
                    This key must match the one configured on the server.
                    This object may only be read or written when
                    hpSwitchAuthenticationEncryptCredentialsMethod is set to a
                    value other than none(0). At most one of
                    hpSwitchTacacsServerKey and hpSwitchTacacsServerKeyEncrypted
                    may be set in any transaction. This object should only be
                    written with an encrypted key previously read from a
                    compatible HP Networking device."
        ::= { hpSwitchTacacsServersEntry 6 }

   hpSwitchTacacsServerAddressType OBJECT-TYPE
        SYNTAX      InetAddressType
        MAX-ACCESS  read-create
        STATUS      current
        DESCRIPTION "Type of TACACS+ Server IP Address stored in
                     hpSwitchTacacsServerAddress."
        ::= { hpSwitchTacacsServersEntry 7 }

    hpSwitchTacacsServerAddress OBJECT-TYPE
        SYNTAX      InetAddress
        MAX-ACCESS  read-create
        STATUS      current
        DESCRIPTION "The IPv4 or IPv6 Address of the TACACS+ server."
        ::= { hpSwitchTacacsServersEntry 8 }

-- ------------------------------------------------------------
    -- Status support for TACACS+ Protocol
-- ------------------------------------------------------------

    hpTacacsStatsServersTable OBJECT-TYPE
        SYNTAX      SEQUENCE OF HpTacacsStatsServersEntry
        MAX-ACCESS  not-accessible
        STATUS      current
        DESCRIPTION "A table containing statistics for the configured
                    TACACS+ servers."
        ::= { hpSwitchAuthenticationMIB 5 }

    hpTacacsStatsServersEntry OBJECT-TYPE
        SYNTAX      HpTacacsStatsServersEntry
        MAX-ACCESS  not-accessible
        STATUS      current
        DESCRIPTION "The information associated with each row in the
                    TACACS+ servers table."
        INDEX       { hpTacacsStatsServerIndex }
        ::= { hpTacacsStatsServersTable 1 }

    HpTacacsStatsServersEntry ::=
        SEQUENCE {
            hpTacacsStatsServerIndex          Integer32,
            hpTacacsStatsTacacsServerIpAddr   IpAddress,
            hpTacacsStatsNumSessOpened        Counter32,
            hpTacacsStatsNumSessClosed        Counter32,
            hpTacacsStatsNumSessAborted       Counter32,
            hpTacacsStatsNumSessErrors        Counter32,
            hpTacacsStatsNumPktsIn            Counter32,
            hpTacacsStatsNumPktsOut           Counter32,
            hpTacacsStatsNumAuthPktsIn        Counter32,
            hpTacacsStatsNumAuthPktsOut       Counter32,
            hpTacacsStatsNumAuthPktsTimedOut  Counter32,
            hpTacacsStatsNumAutzPktsIn        Counter32,
            hpTacacsStatsNumAutzPktsOut       Counter32,
            hpTacacsStatsNumAutzPktsTimedOut  Counter32,
            hpTacacsStatsNumAcctPktsIn        Counter32,
            hpTacacsStatsNumAcctPktsOut       Counter32,
            hpTacacsStatsNumAcctPktsTimedOut  Counter32,
            hpTacacsStatsTacacsServerAdrType  InetAddressType,
            hpTacacsStatsTacacsServerAddr     InetAddress
        }

    hpTacacsStatsServerIndex OBJECT-TYPE
        SYNTAX      Integer32 (1..65535)
        MAX-ACCESS  not-accessible
        STATUS      current
        DESCRIPTION "The index identifying the row in the table."
        ::= { hpTacacsStatsServersEntry 1 }

    hpTacacsStatsTacacsServerIpAddr OBJECT-TYPE
        SYNTAX      IpAddress
        MAX-ACCESS  read-only
        STATUS      current
        DESCRIPTION "The IP address of a TACACS+ Server."
        ::= { hpTacacsStatsServersEntry 2 }

    hpTacacsStatsNumSessOpened OBJECT-TYPE
        SYNTAX      Counter32
        MAX-ACCESS  read-only
        STATUS      current
        DESCRIPTION "The number of authentication, authorization and
                     accounting sessions opened with the server."
        ::= { hpTacacsStatsServersEntry 3 }

    hpTacacsStatsNumSessClosed OBJECT-TYPE
        SYNTAX      Counter32
        MAX-ACCESS  read-only
        STATUS      current
        DESCRIPTION "The number of authentication, authorization and
                     accounting sessions closed  with the server."
        ::= { hpTacacsStatsServersEntry 4 }

    hpTacacsStatsNumSessAborted OBJECT-TYPE
        SYNTAX      Counter32
        MAX-ACCESS  read-only
        STATUS      current
        DESCRIPTION "The number of authentication, authorization and
                     accounting sessions aborted with the server."
        ::= { hpTacacsStatsServersEntry 5 }

    hpTacacsStatsNumSessErrors OBJECT-TYPE
        SYNTAX      Counter32
        MAX-ACCESS  read-only
        STATUS      current
        DESCRIPTION "The number of authentication, authorization and
                     accounting sessions with this server resulted in 
                     an error."
        ::= { hpTacacsStatsServersEntry 6 }

    hpTacacsStatsNumPktsIn OBJECT-TYPE
        SYNTAX      Counter32
        MAX-ACCESS  read-only
        STATUS      current
        DESCRIPTION "The number of responses received from the server."
        ::= { hpTacacsStatsServersEntry 7 }

    hpTacacsStatsNumPktsOut OBJECT-TYPE
        SYNTAX      Counter32
        MAX-ACCESS  read-only
        STATUS      current
        DESCRIPTION "The number of requests sent to the server."
        ::= { hpTacacsStatsServersEntry 8 }

    hpTacacsStatsNumAuthPktsIn OBJECT-TYPE
        SYNTAX      Counter32
        MAX-ACCESS  read-only
        STATUS      current
        DESCRIPTION "The number of authentication responses received from the server."
        ::= { hpTacacsStatsServersEntry 9 }

    hpTacacsStatsNumAuthPktsOut OBJECT-TYPE
        SYNTAX      Counter32
        MAX-ACCESS  read-only
        STATUS      current
        DESCRIPTION "The number of authentication requests sent to the server."
        ::= { hpTacacsStatsServersEntry 10 }

    hpTacacsStatsNumAuthPktsTimedOut OBJECT-TYPE
        SYNTAX      Counter32
        MAX-ACCESS  read-only
        STATUS      current
        DESCRIPTION "The number of authentication requests that timed out due to
                     no response from the server."
        ::= { hpTacacsStatsServersEntry 11 }

    hpTacacsStatsNumAutzPktsIn OBJECT-TYPE
        SYNTAX      Counter32
        MAX-ACCESS  read-only
        STATUS      current
        DESCRIPTION "The number of authorization responses received from the server."
        ::= { hpTacacsStatsServersEntry 12 }

    hpTacacsStatsNumAutzPktsOut OBJECT-TYPE
        SYNTAX      Counter32
        MAX-ACCESS  read-only
        STATUS      current
        DESCRIPTION "The number of authorization requests sent to the server."
        ::= { hpTacacsStatsServersEntry 13 }

    hpTacacsStatsNumAutzPktsTimedOut OBJECT-TYPE
        SYNTAX      Counter32
        MAX-ACCESS  read-only
        STATUS      current
        DESCRIPTION "The number of authorization requests that timed out due to
                     no response from the server."
        ::= { hpTacacsStatsServersEntry 14 }

    hpTacacsStatsNumAcctPktsIn OBJECT-TYPE
        SYNTAX      Counter32
        MAX-ACCESS  read-only
        STATUS      current
        DESCRIPTION "The number of accounting responses received from the server."
        ::= { hpTacacsStatsServersEntry 15 }

    hpTacacsStatsNumAcctPktsOut OBJECT-TYPE
        SYNTAX      Counter32
        MAX-ACCESS  read-only
        STATUS      current
        DESCRIPTION "The number of accounting requests sent to the server."
        ::= { hpTacacsStatsServersEntry 16 }

    hpTacacsStatsNumAcctPktsTimedOut OBJECT-TYPE
        SYNTAX      Counter32
        MAX-ACCESS  read-only
        STATUS      current
        DESCRIPTION "The number of accounting requests that timed out due to
                     no response from the server."
        ::= { hpTacacsStatsServersEntry 17 }

   hpTacacsStatsTacacsServerAdrType OBJECT-TYPE
        SYNTAX      InetAddressType
        MAX-ACCESS  read-only
        STATUS      current
        DESCRIPTION "Type of TACACS+ Server IP Address stored in
                     hpTacacsStatsTacacsServerAddr."
        ::= { hpTacacsStatsServersEntry 18 }

    hpTacacsStatsTacacsServerAddr OBJECT-TYPE
        SYNTAX      InetAddress
        MAX-ACCESS  read-only
        STATUS      current
        DESCRIPTION "The IPv4 or IPv6 Address of the TACACS+ server."
        ::= { hpTacacsStatsServersEntry 19 }

-- ------------------------------------------------------------
    -- Configuration support for RADIUS Protocol
-- ------------------------------------------------------------

    hpSwitchRadiusConfig OBJECT IDENTIFIER ::= { hpSwitchAuthenticationMIB 6 }

    hpSwitchRadiusDeadTime OBJECT-TYPE
        SYNTAX      Integer32 (0..1440)
        MAX-ACCESS  read-write
        STATUS      current
        DESCRIPTION "The length of time in minutes a RADIUS server is skipped
                    over by transaction requests (from 0 up to 24 hours). 
                    Used to improve RADIUS response times when some servers might
                    be unavailable."
        DEFVAL { 0 }
        ::= { hpSwitchRadiusConfig 1 }

    hpSwitchRadiusTimeout OBJECT-TYPE
        SYNTAX      Integer32 (1..15)
        MAX-ACCESS  read-write
        STATUS      current
        DESCRIPTION "The duration in seconds to wait for a response from 
                    the RADIUS server host."
        DEFVAL { 5 }
        ::= { hpSwitchRadiusConfig 2 }

    hpSwitchRadiusRetransmitAttempts OBJECT-TYPE
        SYNTAX      Integer32 (1..5)
        MAX-ACCESS  read-write
        STATUS      current
        DESCRIPTION "Maximum number of retransmission attempts."
        DEFVAL { 3 }
        ::= { hpSwitchRadiusConfig 3 }

    hpSwitchRadiusAuthKey OBJECT-TYPE
        SYNTAX      OCTET STRING (SIZE(0..100))
        MAX-ACCESS  read-write
        STATUS      current
        DESCRIPTION "The key used in encrypting the packets passed between
                    the RADIUS server and the client. This key must match
                    the one configured on the server."
        ::= { hpSwitchRadiusConfig 4 }

    hpSwitchRadiusDynAutzPortNumber OBJECT-TYPE
        SYNTAX      Integer32 (1..65535)
        MAX-ACCESS  read-write
        STATUS      current
        DESCRIPTION "The UDP port number to listen for Disconnect and 
                    Change-of-Authorization messages."
        REFERENCE  "RFC 3576"
        DEFVAL    {3799}
        ::= { hpSwitchRadiusConfig 5 }

    hpSwitchRadiusAuthKeyEncrypted OBJECT-TYPE
        SYNTAX      OCTET STRING (SIZE(0..256))
        MAX-ACCESS  read-write
        STATUS      current
        DESCRIPTION "An encrypted form of the key used in encrypting the
                    packets passed between the RADIUS server and the client.
                    This key must match the one configured on the server.
                    This object may only be read or written when
                    hpSwitchAuthenticationEncryptCredentialsMethod is set to a
                    value other than none(0). At most one of
                    hpSwitchRadiusAuthKey and hpSwitchRadiusAuthKeyEncrypted
                    may be set in any transaction. This object should only be
                    written with an encrypted key previously read from a
                    compatible HP Networking device."
        ::= { hpSwitchRadiusConfig 6 }

    hpSwitchRadiusTracking OBJECT-TYPE
        SYNTAX      TruthValue
        MAX-ACCESS  read-write
        STATUS      current
        DESCRIPTION "To enable or disable the RADIUS service tracking. If this
                     feature is enabled, it is used to send access-request packets
                     at regular intervals to track the availability of server."
        DEFVAL { false }
        ::= { hpSwitchRadiusConfig 10 }

    hpSwitchRadiusTrackingUserName OBJECT-TYPE
         SYNTAX      DisplayString (SIZE(1..64))
         MAX-ACCESS  read-create
         STATUS      current
         DESCRIPTION "This user name will be used to send Access-Request packets to      
                      the RADIUS server to track it."
         DEFVAL { "radius-tracking-user" }
         ::= { hpSwitchRadiusConfig 11 }

    hpSwitchRadiusCppmIdentity OBJECT-TYPE
         SYNTAX      DisplayString (SIZE(0..255))
         MAX-ACCESS  read-write
         STATUS      current
         DESCRIPTION "The cppm identity value to be used during authentication with 
                      cppm server."
         ::= { hpSwitchRadiusConfig 12 }

    hpSwitchRadiusCppmKey OBJECT-TYPE
         SYNTAX      DisplayString (SIZE(0|8..64))
         MAX-ACCESS  read-write
         STATUS      current
         DESCRIPTION "The cppm key value to be used during authentication with 
                      cppm server."
         ::= { hpSwitchRadiusConfig 13 }
    
   hpSwitchRadiusCppmEncryptedKey OBJECT-TYPE
         SYNTAX      DisplayString (SIZE(0..256))
         MAX-ACCESS  read-write
         STATUS      current
         DESCRIPTION "The encrypted cppm key value to be used during authentication 
                      with cppm server.The key value used to set this object should 
                      be read from a compatible HPE netwokring device only."
         ::= { hpSwitchRadiusConfig 14 }

    hpSwitchRadiusDeadTimeInfinite OBJECT-TYPE
        SYNTAX      TruthValue
        MAX-ACCESS  read-write
        STATUS      current
        DESCRIPTION "If this is set to true, a dead RADIUS server is skipped
                    over by transaction requests until the RADIUS server is tracked
                    up and alive by RADIUS tracking. The default value is set
                    to FLASE."
        DEFVAL { false }
        ::= { hpSwitchRadiusConfig 15 }

    hpSwitchRadiusTrackingInterval OBJECT-TYPE
        SYNTAX      Integer32(60..86400)
        MAX-ACCESS  read-write
        STATUS      current
        DESCRIPTION "The regular time interval in seconds at which RADIUS
                     access-request packets are sent to track the availability
                     of RADIUS server. The default time interval is 5 minutes."
        DEFVAL { 60 }
        ::= { hpSwitchRadiusConfig 16 }

    hpSwitchRadiusTrackingPassword OBJECT-TYPE
         SYNTAX      DisplayString (SIZE(0..64))
         MAX-ACCESS  read-write
         STATUS      current
         DESCRIPTION "This password will be used in Access-Request packets
                      sent to the RADIUS server to track it."
         ::= { hpSwitchRadiusConfig 17 }

    hpSwitchRadiusTrackDeadOnly OBJECT-TYPE
        SYNTAX      TruthValue
        MAX-ACCESS  read-write
        STATUS      current
        DESCRIPTION "If this is set to true, RADIUS tracking packets are sent
                     only to dead servers."
        DEFVAL { false }
        ::= { hpSwitchRadiusConfig 18 }

    hpSwitchRadiusTrackReqPktCount OBJECT-TYPE
        SYNTAX      Integer32(1..5)
        MAX-ACCESS  read-write
        STATUS      current
        DESCRIPTION "Number of Access Request Packet to be sent for tracking."
        DEFVAL { 3 }
        ::= { hpSwitchRadiusConfig 19 }

    hpSwitchRadiusTrackPassEncrypt OBJECT-TYPE
        SYNTAX      DisplayString (SIZE(0..256))
        MAX-ACCESS  read-write
        STATUS      current
        DESCRIPTION "The password is configured in the encrypted form.
                     The password after decryption is sent in Access-Request
                     packet to the RADIUS server for tracking.
                     This object can be read or written only when
                     hpSwitchAuthenticationEncryptCredentialsMethod is set to a
                     value other than none(0). At most one of the
                     hpSwitchRadiusTrackingPassword and
                     hpSwitchRadiusTrackPassEncrypt can be set in any
                     transaction. This object should only be written with an
                     encrypted password string previously read from a
                     compatible Networking device."
        ::= { hpSwitchRadiusConfig 20 }

    hpSwitchRadiusFramedIpv4Address OBJECT-TYPE
        SYNTAX      TruthValue
        MAX-ACCESS  read-write
        STATUS      current
        DESCRIPTION "If this is set to true, framedIpv4Address attribute will be added to
                     the access-request packet. The default value is set to FLASE."
        DEFVAL { false }
        ::= { hpSwitchRadiusConfig 21 }

    hpSwitchRadiusFqdnRetry OBJECT-TYPE
        SYNTAX      Integer32 (0..5)
        MAX-ACCESS  read-write
        STATUS      current
        DESCRIPTION "The interval at which the resolution of the FQDN is retried for the radius server 
                     which failed to resolve the FQDN at the time of configuring it. Retry interval is 
                     0-5 minutes. When 0 is set, the FQDN resolution will not be retried.
                     The default value is 3 minutes."
        DEFVAL { 3 }
        ::= { hpSwitchRadiusConfig 22 }

    hpSwitchRadiusTLSTimeout OBJECT-TYPE
        SYNTAX      Integer32 (5..30)
        MAX-ACCESS  read-write
        STATUS      current
        DESCRIPTION "The duration in seconds to wait for a response from 
                     the RADIUS TLS server host."
        DEFVAL { 5 }
        ::= { hpSwitchRadiusConfig 24 }

    hpSwitchRadiusTLSConnectionTimeout OBJECT-TYPE
        SYNTAX      Integer32 (5..30)
        MAX-ACCESS  read-write
        STATUS      current
        DESCRIPTION "The duration in seconds to wait for a response from 
                     the server during TLS session establishment."
        DEFVAL { 5 }
        ::= { hpSwitchRadiusConfig 25 }

    hpSwitchRadiusTLSDeadTime OBJECT-TYPE
        SYNTAX      Integer32 (0..1440)
        MAX-ACCESS  read-write
        STATUS      current
        DESCRIPTION "The length of time in minutes a RADIUS TLS server is skipped
                     over by transaction requests (from 0 up to 24 hours). 
                     Used to improve RADIUS response times when some servers might
                     be unavailable."
        DEFVAL { 0 }
        ::= { hpSwitchRadiusConfig 26 }

     hpSwitchRadiusTLSDeadTimeInfinite OBJECT-TYPE
        SYNTAX      TruthValue
        MAX-ACCESS  read-write
        STATUS      current
        DESCRIPTION "If this is set to true, a dead RADIUS TLS server 
                    is skipped over by transaction requests until the 
                    RADIUS TLS server is tracked up and alive by 
                    RADIUS tracking. The default value is set to FALSE."
        DEFVAL { false }
        ::= { hpSwitchRadiusConfig 27 }

    hpSwitchRadiusServerTable OBJECT-TYPE
        SYNTAX      SEQUENCE OF HpSwitchRadiusServerEntry
        MAX-ACCESS  not-accessible
        STATUS      current
        DESCRIPTION "This table lists a maximum of 3 RADIUS servers."
        ::= { hpSwitchAuthenticationMIB 7 }

    hpSwitchRadiusServerEntry OBJECT-TYPE
        SYNTAX      HpSwitchRadiusServerEntry
        MAX-ACCESS  not-accessible
        STATUS      current
        DESCRIPTION "A RADIUS server table entry."
        INDEX       { hpSwitchRadiusServerIndex }
        ::= { hpSwitchRadiusServerTable 1 }

    HpSwitchRadiusServerEntry ::=
        SEQUENCE {
            hpSwitchRadiusServerIndex             Integer32,
            hpSwitchRadiusServerIpAddr            IpAddress,
            hpSwitchRadiusServerKey               OCTET STRING,
            hpSwitchRadiusServerAuthPortNumber    Integer32,
            hpSwitchRadiusServerAcctPortNumber    Integer32,
            hpSwitchRadiusServerDynAutzEnabled    TruthValue,
            hpSwitchRadiusServerDynAutzTimeWindow Integer32,
            hpSwitchRadiusServerStatus            RowStatus,
            hpSwitchRadiusServerIsOobm            TruthValue,
            hpSwitchRadiusServerKeyEncrypted      OCTET STRING,
            hpSwitchRadiusServerAddrType          InetAddressType,
            hpSwitchRadiusServerAddress           InetAddress,
            hpSwitchRadiusServerDynAutzTimeWindowType INTEGER,
            hpSwitchRadiusServerFqdn              DisplayString,
            hpSwitchRadiusServerIsClearPass       TruthValue,
            hpSwitchRadiusTLSEnable               TruthValue,
            hpSwitchRadiusTLSPort                 Integer32,
            hpSwitchRadiusTLSRetryTimer           Integer32
        }

    hpSwitchRadiusServerIndex OBJECT-TYPE
        SYNTAX      Integer32 (1..65535)
        MAX-ACCESS  not-accessible
        STATUS      current
        DESCRIPTION "The index value which uniquely identifies a row in
                    the RADIUS Servers Table."
        ::= { hpSwitchRadiusServerEntry 1 }

    hpSwitchRadiusServerIpAddr OBJECT-TYPE
        SYNTAX      IpAddress
        MAX-ACCESS  read-create
        STATUS      deprecated 
        DESCRIPTION "The IP address of a RADIUS Server. When the RADIUS server 
                     has been configured with IPv6 address, the value of 
                     this object will be set to Null."
        ::= { hpSwitchRadiusServerEntry 2 }

    hpSwitchRadiusServerKey OBJECT-TYPE
        SYNTAX      OCTET STRING (SIZE(0..100))
        MAX-ACCESS  read-create
        STATUS      current
        DESCRIPTION "The key used in encrypting the packets passed between
                    the RADIUS server and the client. This key must match
                    the one configured on the server."
        ::= { hpSwitchRadiusServerEntry 3 }

    hpSwitchRadiusServerAuthPortNumber OBJECT-TYPE
        SYNTAX      Integer32 (1..65535)
        MAX-ACCESS  read-create
        STATUS      current
        DESCRIPTION "The UDP destination port number to use for sending
                    authentication requests to this RADIUS Server."
        ::= { hpSwitchRadiusServerEntry 4 }

    hpSwitchRadiusServerAcctPortNumber OBJECT-TYPE
        SYNTAX      Integer32 (1..65535)
        MAX-ACCESS  read-create
        STATUS      current
        DESCRIPTION "The UDP destination port number to use for sending
                    accounting requests to this RADIUS server."
        ::= { hpSwitchRadiusServerEntry 5 }

    hpSwitchRadiusServerDynAutzEnabled OBJECT-TYPE
        SYNTAX      TruthValue
        MAX-ACCESS  read-create
        STATUS      current
        DESCRIPTION "This object indicates whether Dynamic Authorization
                    messages (Disconnect-Requests and CoA-Requests) are
                    authorized for processing from this RADIUS Server."
        DEFVAL    {false}
        ::= { hpSwitchRadiusServerEntry 6 }

    hpSwitchRadiusServerDynAutzTimeWindow OBJECT-TYPE
        SYNTAX      Integer32 (0..65535)
        MAX-ACCESS  read-create
        STATUS      current
        DESCRIPTION "A non-zero value indicates that the Event-Timestamp
                    attribute must be used in the dynamic authorization
                    communication exchange between the NAS and the RADIUS
                    server. Such a value determines the time window (in
                    seconds) within which RADIUS packets carrying the 
                    Event-Timestamp attribute will be considered as current
                    and accepted for processing by the NAS and the RADIUS 
                    Server. Zero value disables checking for the 
                    Event-Timestamp attribute. The default time window 
                    is 300 seconds."
        REFERENCE  "RFC 3576"
        DEFVAL    {300}
        ::= { hpSwitchRadiusServerEntry 7 }

    hpSwitchRadiusServerStatus OBJECT-TYPE
        SYNTAX      RowStatus
        MAX-ACCESS  read-create
        STATUS      current
        DESCRIPTION "Status of Servers Table row."
        ::= { hpSwitchRadiusServerEntry 8 }

    hpSwitchRadiusServerIsOobm OBJECT-TYPE
        SYNTAX      TruthValue
        MAX-ACCESS  read-create
        STATUS      current
        DESCRIPTION "This object indicates whether this RADIUS Server
                    is reachable over OOBM (Out Of Band Management) 
                    interface or not. This mib object will be applicable
                    only if there is a physical OOBM port on the device."
        DEFVAL    {false}
        ::= { hpSwitchRadiusServerEntry 9 }

    hpSwitchRadiusServerKeyEncrypted OBJECT-TYPE
        SYNTAX      OCTET STRING (SIZE(0..256))
        MAX-ACCESS  read-create
        STATUS      current
        DESCRIPTION "An encrypted form of the key used in encrypting the
                    packets passed between the RADIUS server and the client.
                    This key must match the one configured on the server.
                    This object may only be read or written when
                    hpSwitchAuthenticationEncryptCredentialsMethod is set to a
                    value other than none(0). At most one of
                    hpSwitchRadiusServerKey and hpSwitchRadiusServerKeyEncrypted
                    may be set in any transaction. This object should only be
                    written with an encrypted key previously read from a
                    compatible HP Networking device."
        ::= { hpSwitchRadiusServerEntry 10 }
 
   hpSwitchRadiusServerAddrType OBJECT-TYPE
        SYNTAX      InetAddressType
        MAX-ACCESS  read-create
        STATUS      current
        DESCRIPTION "Type of RADIUS Server IP Address stored in
                     hpSwitchRadiusServerAddress."
        ::= { hpSwitchRadiusServerEntry 11 }

    hpSwitchRadiusServerAddress OBJECT-TYPE
        SYNTAX      InetAddress
        MAX-ACCESS  read-create
        STATUS      current
        DESCRIPTION "The IPv4 or IPv6 Address of the RADIUS server."
        ::= { hpSwitchRadiusServerEntry 12 }

    hpSwitchRadiusServerDynAutzTimeWindowType OBJECT-TYPE
        SYNTAX       INTEGER {
                         positive(0),
                         plusorminus(1)
                     }
        MAX-ACCESS  read-create
        STATUS      current
        DESCRIPTION "Window type indicates the acceptable window size for
                    dynamic authorization messages. Positive window type
                    will allow messages when time difference between sender
                    Event-TimeStamp and receiver/switch timeStamp is between 
                    0 to +hpSwitchRadiusServerDynAutzTimeWindow.
                    plusorminus type will allow messages when time difference 
                    time difference between sender Event-TimeStamp and 
                    receiver/switch timeStamp is between 
                    0 to +hpSwitchRadiusServerDynAutzTimeWindow.The default
                    window type is positive."
        DEFVAL    {positive}
        ::= { hpSwitchRadiusServerEntry 13 }

    hpSwitchRadiusServerFqdn OBJECT-TYPE
       SYNTAX      DisplayString (SIZE (1..255)) 
       MAX-ACCESS  read-create
       STATUS      current
       DESCRIPTION "The FQDN address of RADIUS Server. When the RADIUS server 
                    has been configured with IPv6 address of IPv4 address, 
                    the value of this object will be set to Null."
         ::= { hpSwitchRadiusServerEntry 14 }

    hpSwitchRadiusServerIsClearPass OBJECT-TYPE
        SYNTAX      TruthValue
        MAX-ACCESS  read-create
        STATUS      current
        DESCRIPTION "This object indicates whether this RADIUS Server
                    is hosted by ClearPass or not.This mib object will be applicable
                    only if there is a Hosted ClearPass server"
        DEFVAL    {false}
        ::= { hpSwitchRadiusServerEntry 15 }

    hpSwitchRadiusTLSEnable OBJECT-TYPE
        SYNTAX      TruthValue
        MAX-ACCESS  read-create
        STATUS      current
        DESCRIPTION  "This object enables the RADSEC protocol and encrypts
                      the RADIUS messages using TLS by establishing a TCP
                      connection with the RADIUS server.
                      By default, it is not enabled."
        DEFVAL     { false }
        ::= { hpSwitchRadiusServerEntry 16 }

    hpSwitchRadiusTLSPort OBJECT-TYPE
        SYNTAX       Integer32 (1025..65535)
        MAX-ACCESS   read-create
        STATUS       current
        DESCRIPTION  "The destination TCP port number to use for establishing
                      a connection with RADIUS TLS server. The default
                      value is 2083."
        DEFVAL     { 2083 }
        ::= { hpSwitchRadiusServerEntry 17 }

    hpSwitchRadiusTLSRetryTimer OBJECT-TYPE
         SYNTAX      Integer32 (0..65535)
         MAX-ACCESS  read-only
         STATUS      current
         DESCRIPTION
                "The number of minutes after which the RADIUS Server TLS
                 connection will be re-established."
         ::= { hpSwitchRadiusServerEntry 18 }

-- The 802.1X tables are deprecated

-- ------------------------------------------------------------
-- Key Management Subsystem chain configuration table
-- ------------------------------------------------------------

    hpSwitchKmsChainConfigTable OBJECT-TYPE
         SYNTAX      SEQUENCE OF HpSwitchKmsChainConfigEntry
         MAX-ACCESS  not-accessible
         STATUS      current
         DESCRIPTION "This table contains configuration objects for
                      Key Management Subsystem chains."
    ::= { hpSwitchAuthenticationMIB 15 }
 
-- ------------------------------------------------------------
-- Key Management Subsystem chain configuration entry
-- ------------------------------------------------------------

    hpSwitchKmsChainConfigEntry OBJECT-TYPE
         SYNTAX      HpSwitchKmsChainConfigEntry
         MAX-ACCESS  not-accessible
         STATUS      current
         DESCRIPTION "KMS chain configuration table entry."
         INDEX { hpSwitchKmsChainId }
    ::= { hpSwitchKmsChainConfigTable 1 }
 
    HpSwitchKmsChainConfigEntry ::=
         SEQUENCE {
            hpSwitchKmsChainId         Integer32,
            hpSwitchKmsChainName       DisplayString,
            hpSwitchKmsChainKeys       Gauge32,
            hpSwitchKmsChainActiveKeys Gauge32,
            hpSwitchKmsChainExpKeys    Gauge32,
            hpSwitchKmsChainStatus     RowStatus
         }

    hpSwitchKmsChainId OBJECT-TYPE
         SYNTAX      Integer32 (0..32767)
         MAX-ACCESS  not-accessible
         STATUS      current
         DESCRIPTION "This object is the KMS chain index. Do not rely
                      on it since it may be removed in the future, when
                      it is possible to use the object hpSwitchKmsChainName 
                      as the index."
    ::= { hpSwitchKmsChainConfigEntry 1 }

    hpSwitchKmsChainName OBJECT-TYPE
         SYNTAX      DisplayString (SIZE(1..32))
         MAX-ACCESS  read-create
         STATUS      current
         DESCRIPTION "This object configures the KMS chain name." 
    ::= { hpSwitchKmsChainConfigEntry 2 }

    hpSwitchKmsChainKeys OBJECT-TYPE
         SYNTAX      Gauge32
         MAX-ACCESS  read-only
         STATUS      current
         DESCRIPTION "Returns the number of keys in the KMS chain." 
    ::= { hpSwitchKmsChainConfigEntry 4 }

    hpSwitchKmsChainActiveKeys OBJECT-TYPE
         SYNTAX      Gauge32
         MAX-ACCESS  read-only
         STATUS      current
         DESCRIPTION "Returns the number of active keys in the KMS chain."
    ::= { hpSwitchKmsChainConfigEntry 5 }

    hpSwitchKmsChainExpKeys OBJECT-TYPE
         SYNTAX      Gauge32
         MAX-ACCESS  read-only
         STATUS      current
         DESCRIPTION "Returns the number of expired keys in the KMS chain."
    ::= { hpSwitchKmsChainConfigEntry 6 }

    hpSwitchKmsChainStatus OBJECT-TYPE
        SYNTAX      RowStatus
        MAX-ACCESS  read-create
        STATUS      current
        DESCRIPTION "The status of the row in the KMS chain configuration table."
                     
    ::= { hpSwitchKmsChainConfigEntry 7 }

-- ------------------------------------------------------------
-- Key Management Subsystem key configuration table
-- ------------------------------------------------------------

    hpSwitchKmsKeyConfigTable OBJECT-TYPE
         SYNTAX      SEQUENCE OF HpSwitchKmsKeyConfigEntry
         MAX-ACCESS  not-accessible
         STATUS      current
         DESCRIPTION "This table contains the configuration objects for
                      the Key Management Subsystem."
    ::= { hpSwitchAuthenticationMIB 16 }
 
-- ------------------------------------------------------------
-- Key Management Subsystem key configuration entry
-- ------------------------------------------------------------

    hpSwitchKmsKeyConfigEntry OBJECT-TYPE
         SYNTAX      HpSwitchKmsKeyConfigEntry
         MAX-ACCESS  not-accessible
         STATUS      current
         DESCRIPTION "KMS configuration table entry."
         INDEX { hpSwitchKmsKeyChainId, hpSwitchKmsKeyId }
    ::= { hpSwitchKmsKeyConfigTable 1 }
 
    HpSwitchKmsKeyConfigEntry ::=
         SEQUENCE {
            hpSwitchKmsKeyChainId      Integer32,
            hpSwitchKmsKeyId           Integer32,
            hpSwitchKmsKeyStr          OCTET STRING,
            hpSwitchKmsKeyStartTime    Unsigned32,
            hpSwitchKmsKeyStopTime     Unsigned32,
            hpSwitchKmsKeyTxStartTime  Unsigned32,
            hpSwitchKmsKeyTxStopTime   Unsigned32,
            hpSwitchKmsKeyStatus       RowStatus,
            hpSwitchKmsKeyEncrypted    OCTET STRING
         }

    hpSwitchKmsKeyChainId OBJECT-TYPE
         SYNTAX      Integer32 (0..32767)
         MAX-ACCESS  not-accessible
         STATUS      current
         DESCRIPTION "This object is the KMS chain index. Do not rely
                      on it since it may be removed in the future, when
                      it is possible to use the object hpSwitchKmsChainName
                      as the index."
    ::= { hpSwitchKmsKeyConfigEntry 1 }

    hpSwitchKmsKeyId OBJECT-TYPE
         SYNTAX      Integer32 (0..255)
         MAX-ACCESS  not-accessible
         STATUS      current
         DESCRIPTION "This object is the KMS key index."
    ::= { hpSwitchKmsKeyConfigEntry 2 }

    hpSwitchKmsKeyStr OBJECT-TYPE
         SYNTAX      OCTET STRING (SIZE(0..16))
         MAX-ACCESS  read-create
         STATUS      current
         DESCRIPTION "This object configures the KMS key chain name." 
    ::= { hpSwitchKmsKeyConfigEntry 3 }

    hpSwitchKmsKeyStartTime OBJECT-TYPE
         SYNTAX      Unsigned32
         MAX-ACCESS  read-create
         STATUS      current
         DESCRIPTION "Start time of the KMS key." 
    ::= { hpSwitchKmsKeyConfigEntry 4 }

    hpSwitchKmsKeyStopTime OBJECT-TYPE
         SYNTAX      Unsigned32
         MAX-ACCESS  read-create
         STATUS      current
         DESCRIPTION "Stop time of the KMS key." 
    ::= { hpSwitchKmsKeyConfigEntry 5 }

    hpSwitchKmsKeyTxStartTime OBJECT-TYPE
         SYNTAX      Unsigned32
         MAX-ACCESS  read-create
         STATUS      current
         DESCRIPTION "Start time of the transmission for the KMS key." 
    ::= { hpSwitchKmsKeyConfigEntry 6 }

    hpSwitchKmsKeyTxStopTime OBJECT-TYPE
         SYNTAX      Unsigned32
         MAX-ACCESS  read-create
         STATUS      current
         DESCRIPTION "Stop time of the transmission for the KMS key." 
    ::= { hpSwitchKmsKeyConfigEntry 7 }

    hpSwitchKmsKeyStatus OBJECT-TYPE
        SYNTAX      RowStatus
        MAX-ACCESS  read-create
        STATUS      current
        DESCRIPTION "Row Status of the KMS chain configuration table."
    ::= { hpSwitchKmsKeyConfigEntry 8 }

    hpSwitchKmsKeyEncrypted OBJECT-TYPE
         SYNTAX      OCTET STRING (SIZE(0..256))
         MAX-ACCESS  read-create
         STATUS      current
         DESCRIPTION "An encrypted form of the KMS key. This object may only be
                     read or written when
                     hpSwitchAuthenticationEncryptCredentialsMethod is set to a
                     value other than none(0). At most one of
                     hpSwitchKmsKeyStr and hpSwitchKmsKeyEncrypted may be set
                     in any transaction. This object should only be written
                     with an encrypted key previously read from a compatible
                     HP Networking device."
    ::= { hpSwitchKmsKeyConfigEntry 9 }

-- ------------------------------------------------------------
-- OSPF Interface authentication configuration table
-- ------------------------------------------------------------

    hpSwitchOspfIfAuthTable OBJECT-TYPE
         SYNTAX      SEQUENCE OF HpSwitchOspfIfAuthEntry
         MAX-ACCESS  not-accessible
         STATUS      current
         DESCRIPTION "This table supplements the OSPF interface 
                      configuration table."
    ::= { hpSwitchAuthenticationMIB 17 }
 
    hpSwitchOspfIfAuthEntry OBJECT-TYPE
         SYNTAX      HpSwitchOspfIfAuthEntry
         MAX-ACCESS  not-accessible
         STATUS      current
         DESCRIPTION "OSPF interface authentication 
                      configuration table entry."
         AUGMENTS { ospfIfEntry }
    ::= { hpSwitchOspfIfAuthTable 1 }
 
    HpSwitchOspfIfAuthEntry ::=
         SEQUENCE {
            hpSwitchOspfIfAuthChain DisplayString,
            hpSwitchOspfIfAuthKeyEncrypted OCTET STRING
         }

    hpSwitchOspfIfAuthChain OBJECT-TYPE
         SYNTAX      DisplayString (SIZE(0..32))
         MAX-ACCESS  read-create
         STATUS      current
         DESCRIPTION "This object configures the KMS chain name for
                      OSPF interfaces." 
    ::= { hpSwitchOspfIfAuthEntry 1 }

    hpSwitchOspfIfAuthKeyEncrypted OBJECT-TYPE
         SYNTAX       OCTET STRING (SIZE (0..256))
         MAX-ACCESS   read-create
         STATUS       current
         DESCRIPTION  "The object represents the encrypted format of
                       authentication key stored in the object ospfIfAuthKey.
                       This object may only be read or written when
                       hpSwitchAuthenticationEncryptCredentialsMethod is set to
                       a value other than none(0). This object should only be
                       written with an encrypted key."
    ::= { hpSwitchOspfIfAuthEntry 2 }

-- ------------------------------------------------------------
-- OSPF Virtual Interface authentication configuration table
-- ------------------------------------------------------------

    hpSwitchOspfVirtIfAuthTable OBJECT-TYPE
         SYNTAX      SEQUENCE OF HpSwitchOspfVirtIfAuthEntry
         MAX-ACCESS  not-accessible
         STATUS      current
         DESCRIPTION "This table supplements the OSPF virtual 
                      interface configuration table."
    ::= { hpSwitchAuthenticationMIB 18 }
 
    hpSwitchOspfVirtIfAuthEntry OBJECT-TYPE
         SYNTAX      HpSwitchOspfVirtIfAuthEntry
         MAX-ACCESS  not-accessible
         STATUS      current
         DESCRIPTION "OSPF virtual interface authentication 
                      configuration table entry."
         AUGMENTS { ospfVirtIfEntry }
    ::= { hpSwitchOspfVirtIfAuthTable 1 }
 
    HpSwitchOspfVirtIfAuthEntry ::=
         SEQUENCE {
            hpSwitchOspfVirtIfAuthChain DisplayString,
            hpSwitchOspfVirtIfAuthKeyEncrypted OCTET STRING
         }

    hpSwitchOspfVirtIfAuthChain OBJECT-TYPE
         SYNTAX      DisplayString (SIZE(0..32))
         MAX-ACCESS  read-create
         STATUS      current
         DESCRIPTION "This object configures the KMS chain name for
                      OSPF virtual interfaces." 
    ::= { hpSwitchOspfVirtIfAuthEntry 1 }

    hpSwitchOspfVirtIfAuthKeyEncrypted OBJECT-TYPE
        SYNTAX       OCTET STRING (SIZE(0..256))
        MAX-ACCESS   read-create
        STATUS       current
        DESCRIPTION  "This object represents the encrypted format of
                      authentication key stored in the object ospfVirtIfAuthKey.
                      This object may only be read or written when
                      hpSwitchAuthenticationEncryptCredentialsMethod is set to a
                      value other than none(0). This object should only be
                      written with an encrypted key."
   ::= { hpSwitchOspfVirtIfAuthEntry 2 }

-- ------------------------------------------------------------
    -- Configuration support for SSL server
-- ------------------------------------------------------------

    hpSwitchSslConfig OBJECT IDENTIFIER ::= { hpSwitchAuthenticationMIB 12 }        
    
    hpSwitchSslAdminStatus OBJECT-TYPE
        SYNTAX      INTEGER {
                        disabled(1),
                        enabled(2)
                    }
        MAX-ACCESS  read-write
        STATUS      current
        DESCRIPTION "This objects specifies the desired operational 
                     status of SSL."
        DEFVAL     {1}
        ::= { hpSwitchSslConfig 1 }   
        

   hpSwitchSslPortNumber OBJECT-TYPE
        SYNTAX      Integer32 (1..65535)
        MAX-ACCESS  read-write
        STATUS      current
        DESCRIPTION "The port number on which the SSL server should listen 
                     for connection requests."
        DEFVAL { 443 }
        ::= { hpSwitchSslConfig 2 } 

-- ------------------------------------------------------------
    -- Configuration support for Certificates 
-- ------------------------------------------------------------
                
    hpSwitchCertConfig OBJECT IDENTIFIER ::= { hpSwitchAuthenticationMIB 13 }        
        
    hpSwitchServerCertificateOperation OBJECT-TYPE
        SYNTAX      INTEGER {
                        none(1),
                        useInstalled(2),
                        createAndUseSelfSigned(3),
                        createCACertReq(4),
                        applyCASignedCert(5),
                        abortCASignedRequest(6)
                    }
        MAX-ACCESS  read-write
        STATUS      current
        DESCRIPTION "When this object is read, it returns the last value that was written.
                     If a value was not set previously, then the object value will be 'none'(1).
                     The object supports the following values and actions: 
                     'none' - no action is taken, null operation.
                     
                     'useInstalled' - This causes the switch to use a previously
                     installed server certificate, if one is present. 

                     'createAndUseSelfSigned' - This causes the switch to 
                     create a new self-signed certificate based on the
                     hpSwitchServerNewCertificate parameters and use it.

                     'createCACertReq' - This causes the switch to create
                     a certificate request, which is to be signed by a CA
                     authority, based on the hpSwitchServerNewCertificate  
                     parameters. The user must subsequently download the signed 
                     certificate to complete certificate creation process.

                     'applyCASignedCert' - This causes the switch to process the
                     user's response to a signed certificate from a CA to complete
                     the certificate creation process. 

                     'abortCASignedRequest' - This causes the switch to abort
                     the certificate request procedure, which was initiated on
                     createAndUseCASigned set."

        ::= { hpSwitchCertConfig 1 }
        
    hpSwitchServerNewRSAKeyOperation OBJECT-TYPE
        SYNTAX      INTEGER {
                        useInstalled(1),
                        createBits512(2),
                        createBits768(3),
                        createBits1024(4),
                        createBits2048(5)
                    }
        MAX-ACCESS  read-write
        STATUS      current
        DESCRIPTION "This object when will returns a value either 'useInstalled'(1) or 
                     'createBits1024'(4). 
                     The value 'useInstalled'(1) is returned when 
                     a certificate RSA key already exists on switch. 
                     The value 'createBits1024'(4) is returned when no certificate RSA key
                     exists on switch. 

                     When user configuresthe values, the value triggers the following action:
                     
                     'useInstalled' - The switch will use the currently configured RSA key
                     that is already present on the switch.
                     
                     'createBits512' - This value is deprecated and no longer supported. 
                     
                     'createBits768' - This value is deprecated and no longer supported.
                     
                     'createBits1024' - This value specifies the creation of a new RSA 
                     key of length 1024-bit.
                     
                     'createBits2048' - This value specifies the creation of a new RSA 
                     key of length 2048-bit."
        ::= { hpSwitchCertConfig 2 }

    hpSwitchServerNewCertificateStartDate OBJECT-TYPE
        SYNTAX      DateAndTime
        MAX-ACCESS  read-write
        STATUS      current
        DESCRIPTION "Specifies the start date of validity for a new server 
                     certificate."
        ::= { hpSwitchCertConfig 3 }

    hpSwitchServerNewCertificateEndDate OBJECT-TYPE
        SYNTAX      DateAndTime
        MAX-ACCESS  read-write
        STATUS     current
        DESCRIPTION "Specifies the end date of validity for a new server 
                     certificate."
        ::= { hpSwitchCertConfig 4 }

    hpSwitchServerNewCertificateCommonName OBJECT-TYPE
        SYNTAX      OCTET STRING (SIZE(1..40))
        MAX-ACCESS  read-write
        STATUS      deprecated
        DESCRIPTION "Specifies the common name for a new server 
                     certificate."
        ::= { hpSwitchCertConfig 5 }

    hpSwitchServerNewCertificateOrgUnit OBJECT-TYPE
        SYNTAX      OCTET STRING (SIZE(1..40))
        MAX-ACCESS  read-write
        STATUS      deprecated
        DESCRIPTION "Specifies the organization for a new server
                     certificate."
        ::= { hpSwitchCertConfig 6 }

    hpSwitchServerNewCertificateOrgName OBJECT-TYPE
        SYNTAX      OCTET STRING (SIZE(1..40))
        MAX-ACCESS  read-write
        STATUS      deprecated
        DESCRIPTION "Specifies the organization name for a new server
                     certificate."
        ::= { hpSwitchCertConfig 7 }

    hpSwitchServerNewCertificateCityName OBJECT-TYPE
        SYNTAX      OCTET STRING (SIZE(1..40))
        MAX-ACCESS  read-write
        STATUS      deprecated
        DESCRIPTION "Specifies the city for a new server certificate."
        ::= { hpSwitchCertConfig 8 }

    hpSwitchServerNewCertificateStateName OBJECT-TYPE
        SYNTAX      OCTET STRING (SIZE(1..40))
        MAX-ACCESS  read-write
        STATUS      deprecated
        DESCRIPTION "Specifies the state for a new server certificate."
        ::= { hpSwitchCertConfig 9 }

    hpSwitchServerNewCertificateCountryCode OBJECT-TYPE
        SYNTAX      OCTET STRING (SIZE(2))
        MAX-ACCESS  read-write
        STATUS     current
        DESCRIPTION "Specifies the 2-letter ISO country code of the server certificate."
        ::= { hpSwitchCertConfig 10 }
    hpSwitchServerNewCertCommonName OBJECT-TYPE
        SYNTAX      OCTET STRING (SIZE(1..200))
        MAX-ACCESS  read-write
        STATUS     current
        DESCRIPTION "Specifies the common name for a new server 
                     certificate."
        ::= { hpSwitchCertConfig 11 }

    hpSwitchServerNewCertOrgUnit OBJECT-TYPE
        SYNTAX      OCTET STRING (SIZE(1..200))
        MAX-ACCESS  read-write
        STATUS     current
        DESCRIPTION "Specifies the organization for a new server
                     certificate."
        ::= { hpSwitchCertConfig 12 }

    hpSwitchServerNewCertOrgName OBJECT-TYPE
        SYNTAX      OCTET STRING (SIZE(1..200))
        MAX-ACCESS  read-write
        STATUS     current
        DESCRIPTION "Specifies the organization name for a new server
                     certificate."
        ::= { hpSwitchCertConfig 13 }

    hpSwitchServerNewCertCityName OBJECT-TYPE
        SYNTAX      OCTET STRING (SIZE(1..200))
        MAX-ACCESS  read-write
        STATUS     current
        DESCRIPTION "Specifies the city for a new server certificate."
        ::= { hpSwitchCertConfig 14 }

    hpSwitchServerNewCertStateName OBJECT-TYPE
        SYNTAX      OCTET STRING (SIZE(1..200))
        MAX-ACCESS  read-write
        STATUS     current
        DESCRIPTION "Specifies the state for a new server certificate."
        ::= { hpSwitchCertConfig 15 }

    hpSwitchServerNewCertKeySizeExists OBJECT-TYPE
        SYNTAX      TruthValue
        MAX-ACCESS  read-write
        STATUS      current
        DESCRIPTION "Specifies whether the given key size already exist."
        DEFVAL      {false}
        ::= { hpSwitchCertConfig 16 }

-- ------------------------------------------------------------
    -- Certificate Status
-- ------------------------------------------------------------
    hpSwitchCertStatus OBJECT IDENTIFIER ::= { hpSwitchAuthenticationMIB  14}

    hpSwitchServerCertificateType OBJECT-TYPE
        SYNTAX      INTEGER {
                        none(1),
                        pendCaSigned(2),
                        selfSigned(3),
                        caSigned(4)
                    }
        MAX-ACCESS  read-only
        STATUS      current
        DESCRIPTION "Specifies the type of server certificate the switch is 
                     currently using as follows:
                     
                    'none' - no server certificate is present.
                    
                    'pendCaSigned' - switch is waiting for user to offer 
                    CA-signed certificate request.
                    
                    'selfSigned' - a self-signed server certificate is being 
                    used.
                    
                    'caSigned' - a CA-signed server certificate is being 
                    used."
        ::= { hpSwitchCertStatus 1 }
    
    hpSwitchServerCertificateRSAKeySize OBJECT-TYPE
        SYNTAX       INTEGER {
                         none(0),
                         bits512(1),
                         bits768(2),
                         bits1024(3),
                         bits2048(4)
                     }
        MAX-ACCESS   read-only
        STATUS       current
        DESCRIPTION  "Specifies the RSA key length of the public key contained 
                      in the certificate as follows:
                      
                      'none'     - no certificate is present
                      'Bits512'  - certificate has a 512-bit public key
                      'Bits768'  - certificate has a 768-bit public key 
                      'Bits1024' - certificate has a 1024-bit public key
                      'Bits2048' - certificate has a 2048-bit public key"
        ::= { hpSwitchCertStatus 2 }                      
        
    hpSwitchServerCertificateSerialNumber  OBJECT-TYPE
        SYNTAX       OCTET STRING (SIZE(0..40))
        MAX-ACCESS   read-only 
        STATUS       current
        DESCRIPTION  "Specifies the serial number of installed server 
                     certificate."
        ::= { hpSwitchCertStatus 3 }

    hpSwitchServerCertificateStartDate OBJECT-TYPE
        SYNTAX       DateAndTime
        MAX-ACCESS   read-only 
        STATUS       current
        DESCRIPTION  "Specifies the start date of validity of installed server 
                     certificate."
        ::= { hpSwitchCertStatus 4 }

    hpSwitchServerCertificateEndDate OBJECT-TYPE
        SYNTAX       DateAndTime
        MAX-ACCESS   read-only
        STATUS       current
        DESCRIPTION  "Specifies the end date of validity of installed server 
                     server certificate."
        ::= { hpSwitchCertStatus 5 }

    hpSwitchServerCertificateCommonName OBJECT-TYPE
        SYNTAX       OCTET STRING (SIZE(0..40))
        MAX-ACCESS   read-only
        STATUS       current
        DESCRIPTION  "Specifies the common name of installed server 
                     certificate."
        ::= { hpSwitchCertStatus 6 }

    hpSwitchServerCertificateOrgUnit OBJECT-TYPE
        SYNTAX       OCTET STRING (SIZE(0..40))
        MAX-ACCESS   read-only
        STATUS      current
        DESCRIPTION  "Specifies the organization of installed server                    
                     certificate."
        ::= { hpSwitchCertStatus 7 }

    hpSwitchServerCertificateOrgName OBJECT-TYPE
        SYNTAX       OCTET STRING (SIZE(0..40))
        MAX-ACCESS   read-only
        STATUS      current
        DESCRIPTION  "Specifies the organization name of installed server                    
                     certificate."
        ::= { hpSwitchCertStatus 8 }

    hpSwitchServerCertificateCityName OBJECT-TYPE
        SYNTAX       OCTET STRING (SIZE(0..40))
        MAX-ACCESS   read-only
        STATUS       current
        DESCRIPTION  "Specifies the city of installed server certificate."
        ::= { hpSwitchCertStatus 9 }

    hpSwitchServerCertificateStateName OBJECT-TYPE
        SYNTAX       OCTET STRING (SIZE(0..40))
MAX-ACCESS   read-only 
STATUS      current
        DESCRIPTION  "Specifies the state of installed server certificate."
        ::= { hpSwitchCertStatus 10 }

    hpSwitchServerCertificateCountryCode OBJECT-TYPE
        SYNTAX       OCTET STRING (SIZE(0..40))
        MAX-ACCESS   read-only
        STATUS       current
        DESCRIPTION  "Specifies the 2-letter ISO country code of installed 
                     server certificate."
        ::= { hpSwitchCertStatus 11 }
        
    hpSwitchServerCertificateFingerprintMD5 OBJECT-TYPE
        SYNTAX       OCTET STRING (SIZE(0..48))
        MAX-ACCESS   read-only
        STATUS       current
        DESCRIPTION  "Specifies the MD5 fingerprint of installed server 
                     certificate."
        ::= { hpSwitchCertStatus 12 }

    hpSwitchServerCertificateFingerprintSHA1 OBJECT-TYPE
        SYNTAX       OCTET STRING (SIZE(0..51))
        MAX-ACCESS   read-only
        STATUS       current
        DESCRIPTION  "Specifies the SHA1 fingerprint of installed server 
                     certificate."
        ::= { hpSwitchCertStatus 13 }        

-- ------------------------------------------------------------
    -- Front Panel Security
-- ------------------------------------------------------------
    hpSwitchFrontPanelSecurity OBJECT IDENTIFIER ::= { hpSwitchAuthenticationMIB 26 }

    hpSwitchFpsPasswordClear OBJECT-TYPE
        SYNTAX      INTEGER {
                        enable(0),
                        enablewithreset(1),
                        disable(2)
                    }
        MAX-ACCESS  read-write
        STATUS      current
        DESCRIPTION "This object enables or disables the front panel security
                     password clear command."
        DEFVAL     {enable}
        ::= { hpSwitchFrontPanelSecurity 1 }   

    hpSwitchFpsFactoryReset OBJECT-TYPE
        SYNTAX      INTEGER {
                        enable(0),
                        disable(1)
                    }
        MAX-ACCESS  read-write
        STATUS      current
        DESCRIPTION "This object enables or disables the front panel security 
                     factory reset command."
        DEFVAL     {enable}
        ::= { hpSwitchFrontPanelSecurity 2 }   
        
    hpSwitchFpsPasswordRecovery OBJECT-TYPE
        SYNTAX      INTEGER {
                        off(0),
                        normal(1),
                        strong(2)
                    }
        MAX-ACCESS  read-write
        STATUS      current
        DESCRIPTION "This object enables or disables the front panel security 
                     password recovery command."
        DEFVAL     {strong}
        ::= { hpSwitchFrontPanelSecurity 3 }   

    hpSwitchFpsDiagnosticResetClearButton OBJECT-TYPE
        SYNTAX      INTEGER {
                        enable(0),
                        disable(1)
                    }
        MAX-ACCESS  read-write
        STATUS      current
        DESCRIPTION "This object enables or disables the front panel security 
                     diagnostic reset clear button command."
        DEFVAL     {enable}
        ::= { hpSwitchFrontPanelSecurity 4 }   

    hpSwitchFpsDiagnosticResetSerialConsole OBJECT-TYPE
        SYNTAX      INTEGER {
                        enable(0),
                        disable(1)
                    }
        MAX-ACCESS  read-write
        STATUS      current
        DESCRIPTION "This object enables or disables the front panel security 
                     diagnostic reset serial console command."
        DEFVAL     {enable}
        ::= { hpSwitchFrontPanelSecurity 5 }   

    hpSwitchFpsDisplayInConfig OBJECT-TYPE
        SYNTAX      INTEGER {
                        enable(0),
                        disable(1)
                    }
        MAX-ACCESS  read-write
        STATUS      current
        DESCRIPTION "This object enables or disables the front panel security
                     display in config command."
        DEFVAL     {disable}
        ::= { hpSwitchFrontPanelSecurity 6 }   

-- ------------------------------------------------------------
-- User Config Table
-- ------------------------------------------------------------

    hpicfSwitchUserConfigTable OBJECT-TYPE
         SYNTAX      SEQUENCE OF HpicfSwitchUserConfigEntry
         MAX-ACCESS  not-accessible
         STATUS      current
         DESCRIPTION "This table supplements the manager/operator name/password. The manager/operator password are limited to the CLI interface through Console and Menu interface, and web."
    ::= { hpSwitchAuthenticationMIB 19 }

    hpicfSwitchUserConfigEntry OBJECT-TYPE
         SYNTAX      HpicfSwitchUserConfigEntry
         MAX-ACCESS  not-accessible
         STATUS      current
         DESCRIPTION "Manager/operator name/password table entry."
         INDEX { hpicfSwitchUserConfigIndex }
    ::= { hpicfSwitchUserConfigTable 1 }

       HpicfSwitchUserConfigEntry ::=
        SEQUENCE {
            hpicfSwitchUserConfigIndex      Integer32,
            hpicfSwitchUserName             OCTET STRING,
            hpicfSwitchOperatorName         OCTET STRING,
            hpicfSwitchUserPassword         OCTET STRING,
            hpicfSwitchOperatorPassword     OCTET STRING,
            hpicfSwitchUserConfigStatus     RowStatus,
            hpicfSwitchPortAccessName       OCTET STRING,
            hpicfSwitchPortAccessPassword   OCTET STRING,
            hpicfSwitchUserPasswordHashType        INTEGER,
            hpicfSwitchOperatorPasswordHashType    INTEGER,
            hpicfSwitchPortAccessPasswordHashType  INTEGER,
            hpicfSwitchUserPasswordEncrypted       OCTET STRING,
            hpicfSwitchOperatorPasswordEncrypted   OCTET STRING,
            hpicfSwitchPortAccessPasswordEncrypted OCTET STRING,
            hpicfSwitchBypassUsername              INTEGER,
            hpicfSwitchUserPwdAgingInterval        Integer32,
            hpicfSwitchOperatorPwdAgingInterval    Integer32,
            hpicfSwitchUserPwdLengthValue          Integer32,
            hpicfSwitchOperatorPwdLengthValue      Integer32,
            hpicfSwitchNonPlaintextSha256          INTEGER,
            hpicfSwitchUserPasswordHashSha256      OCTET STRING,
            hpicfSwitchOperatorPasswordHashSha256  OCTET STRING
        }

    hpicfSwitchUserConfigIndex OBJECT-TYPE
        SYNTAX      Integer32 (1..65535)
        MAX-ACCESS  not-accessible
        STATUS      current
        DESCRIPTION "The index value uniquely identifies a row in the User Config table, currently limited to a value of 1."
        ::= { hpicfSwitchUserConfigEntry 1 }

    hpicfSwitchUserName OBJECT-TYPE
        SYNTAX      OCTET STRING (SIZE(0..1024))
        MAX-ACCESS  read-create
        STATUS      current
        DESCRIPTION "The User Name, in ASCII format. The exact size of
                    this object is implementation dependent; consult
                    the product documentation to determine the supported
                    size for a specific product."
        ::= { hpicfSwitchUserConfigEntry 2 }

    hpicfSwitchOperatorName OBJECT-TYPE
        SYNTAX      OCTET STRING (SIZE(0..1024))
        MAX-ACCESS  read-create
        STATUS      current
        DESCRIPTION "The Operator Name, in ASCII format. The exact size
                    of this object is implementation dependent; consult
                    the product documentation to determine the supported
                    size for a specific product."
        ::= { hpicfSwitchUserConfigEntry 3 }  

    hpicfSwitchUserPassword OBJECT-TYPE
        SYNTAX      OCTET STRING (SIZE(0..1024))
        MAX-ACCESS  read-create
        STATUS      current
        DESCRIPTION "The User Password, in ASCII format. The exact size
                    of this object is implementation dependent; consult
                    the product documentation to determine the supported 
                    size for a specific product."
        ::= { hpicfSwitchUserConfigEntry 4 }

    hpicfSwitchOperatorPassword OBJECT-TYPE
        SYNTAX      OCTET STRING (SIZE(0..1024))
        MAX-ACCESS  read-create
        STATUS      current
        DESCRIPTION "The Operator Password, in ASCII format. The exact
                    size of this object is implementation dependent;
                    consult the product documentation to determine the
                    supported size for a specific product."
        ::= { hpicfSwitchUserConfigEntry 5 }

    hpicfSwitchUserConfigStatus OBJECT-TYPE
        SYNTAX      RowStatus
        MAX-ACCESS  read-create
        STATUS      current
        DESCRIPTION "Status of User Config Table row."
        ::= { hpicfSwitchUserConfigEntry 6 }

    hpicfSwitchPortAccessName OBJECT-TYPE
        SYNTAX      OCTET STRING (SIZE(0..1024))
        MAX-ACCESS  read-create
        STATUS      current
        DESCRIPTION "The Port-Access Name, ASCII format. The exact size
                    of this object is implementation dependent; consult
                    the product documentation to determine the supported
                    size for a specific product."
        ::= { hpicfSwitchUserConfigEntry 7 } 
        

    hpicfSwitchPortAccessPassword OBJECT-TYPE
        SYNTAX      OCTET STRING (SIZE(0..1024))
        MAX-ACCESS  read-create
        STATUS      current
        DESCRIPTION "The Port-Access Password, in ASCII format. The 
                     exact size of this object is implementation 
                     dependent; consult the product documentation to 
                     determine the supported size for a specific 
                     product."
        ::= { hpicfSwitchUserConfigEntry 8 }

    hpicfSwitchUserPasswordHashType OBJECT-TYPE
        SYNTAX      INTEGER{
                       unknown(0),
                       plainText(1),
                       sha1(3),
                       sha256(4)
                   }                    
        MAX-ACCESS  read-create
        STATUS      current
        DESCRIPTION "The hash-type of the User Password."
        DEFVAL      {plainText} 
        ::= { hpicfSwitchUserConfigEntry 9 }

     hpicfSwitchOperatorPasswordHashType OBJECT-TYPE
        SYNTAX      INTEGER{
                       unknown(0),
                       plainText(1),
                       sha1(3),
                       sha256(4)
                   }                    
        MAX-ACCESS  read-create
        STATUS      current
        DESCRIPTION "The hash-type of the Operator Password."
        DEFVAL      {plainText}
        ::= { hpicfSwitchUserConfigEntry 10 }
       
     hpicfSwitchPortAccessPasswordHashType OBJECT-TYPE
        SYNTAX      INTEGER{
                       unknown(0),
                       plainText(1)
                   }
        MAX-ACCESS  read-create
        STATUS      current
        DESCRIPTION "The hash-type of the Port-Access Password."
        DEFVAL      {plainText}
        ::= { hpicfSwitchUserConfigEntry 11 }

    hpicfSwitchUserPasswordEncrypted OBJECT-TYPE
        SYNTAX      OCTET STRING (SIZE(0..256))
        MAX-ACCESS  read-create
        STATUS      current
        DESCRIPTION "An encrypted form of the user password. The exact size
                    of this object is implementation dependent; consult
                    the product documentation to determine the supported 
                    size for a specific product.
                    This object may only be read or written when
                    hpSwitchAuthenticationEncryptCredentialsMethod is set to a
                    value other than none(0). At most one of
                    hpicfSwitchUserPassword and hpicfSwitchUserPasswordEncrypted
                    may be set in any transaction. This object should only be
                    written with an encrypted password previously read from a
                    compatible HP Networking device."
        ::= { hpicfSwitchUserConfigEntry 12 }

    hpicfSwitchOperatorPasswordEncrypted OBJECT-TYPE
        SYNTAX      OCTET STRING (SIZE(0..256))
        MAX-ACCESS  read-create
        STATUS      current
        DESCRIPTION "An encrypted form of the operator password. The exact
                    size of this object is implementation dependent;
                    consult the product documentation to determine the
                    supported size for a specific product.
                    This object may only be read or written when
                    hpSwitchAuthenticationEncryptCredentialsMethod is set to a
                    value other than none(0). At most one of
                    hpicfSwitchOperatorPassword and 
                    hpicfSwitchOperatorPasswordEncrypted may be set in any
                    transaction. This object should only be written with an
                    encrypted password previously read from a compatible
                    HP Networking device."
        ::= { hpicfSwitchUserConfigEntry 13 }

    hpicfSwitchPortAccessPasswordEncrypted OBJECT-TYPE
        SYNTAX      OCTET STRING (SIZE(0..256))
        MAX-ACCESS  read-create
        STATUS      current
        DESCRIPTION "An encrypted form of the port-access password. The 
                     exact size of this object is implementation 
                     dependent; consult the product documentation to 
                     determine the supported size for a specific 
                     product. This object may only be read or written when
                     hpSwitchAuthenticationEncryptCredentialsMethod is set to a
                     value other than none(0). At most one of
                     hpicfSwitchPortAccessPassword and 
                     hpicfSwitchPortAccessPasswordEncrypted may be set in any
                     transaction. This object should only be written with an
                     encrypted password previously read from a compatible
                     HP Networking device."
        ::= { hpicfSwitchUserConfigEntry 14 }
     
    hpicfSwitchBypassUsername OBJECT-TYPE
        SYNTAX      INTEGER{
                       enable(1),
                       disable(2)
                   }
        MAX-ACCESS  read-create
        STATUS      current
        DESCRIPTION "This object controls bypassing of the username while 
                     accessing the switch to get  Operator or Manager access.
                     When enabled, the Manager level and Operator level 
                     usernames are bypassed and authentication based on 
                     password takes place. 
                     If custom usernames are configured, this configuration is
                     ignored and authentication based on both username and
                     password takes place. 
                     The default value is 'disable' and user is authenticated 
                     based on both username and password."
        DEFVAL      {disable}
        ::= { hpicfSwitchUserConfigEntry 15 }
        
     
   hpicfSwitchUserPwdAgingInterval   OBJECT-TYPE
        SYNTAX      Integer32 (0..365)
        MAX-ACCESS  read-create
        STATUS      current
        DESCRIPTION "This object holds the manager password aging value."
        ::= { hpicfSwitchUserConfigEntry 16 }
     
   hpicfSwitchOperatorPwdAgingInterval   OBJECT-TYPE
        SYNTAX      Integer32 (0..365)
        MAX-ACCESS  read-create
        STATUS      current
        DESCRIPTION "This object holds the operator password aging value."
        ::= { hpicfSwitchUserConfigEntry 17 }
     
   hpicfSwitchUserPwdLengthValue   OBJECT-TYPE
        SYNTAX      Integer32 (15..64)
        MAX-ACCESS  read-create
        STATUS      current
        DESCRIPTION "This object holds length of the manager password. " 
        DEFVAL      { 15 }
        ::= { hpicfSwitchUserConfigEntry 18 }
     
   hpicfSwitchOperatorPwdLengthValue   OBJECT-TYPE
        SYNTAX      Integer32 (8..64)
        MAX-ACCESS  read-create
        STATUS      current
        DESCRIPTION "This object holds length of the operator password. " 
        DEFVAL      { 8 }
        ::= { hpicfSwitchUserConfigEntry 19 }

   hpicfSwitchNonPlaintextSha256 OBJECT-TYPE
        SYNTAX      INTEGER{
                       enable(1),
                       disable(2)
                   }
        MAX-ACCESS  read-create
        STATUS      current
        DESCRIPTION "This object enables storing the password in SHA-256 form."
        DEFVAL      {disable}
        ::= { hpicfSwitchUserConfigEntry 20 }

   hpicfSwitchUserPasswordHashSha256 OBJECT-TYPE
        SYNTAX      OCTET STRING (SIZE(0..1024))
        MAX-ACCESS  read-create
        STATUS      current
        DESCRIPTION "The SHA256 hash-type of the Manager Password."
        ::= { hpicfSwitchUserConfigEntry 21 }

   hpicfSwitchOperatorPasswordHashSha256 OBJECT-TYPE
        SYNTAX      OCTET STRING (SIZE(0..1024))
        MAX-ACCESS  read-create
        STATUS      current
        DESCRIPTION "The SHA256 hash-type of the Operator Password."
        ::= { hpicfSwitchUserConfigEntry 22 }

-- ------------------------------------------------------------
-- AAA Server Group Table
-- ------------------------------------------------------------

    hpSwitchAAAServerGroupTable OBJECT-TYPE
        SYNTAX      SEQUENCE OF HpSwitchAAAServerGroupEntry
        MAX-ACCESS  not-accessible
        STATUS      current
        DESCRIPTION "This table lists the RADIUS server groups."
        ::= { hpSwitchAuthenticationMIB 20 }

   hpSwitchAAAServerGroupEntry OBJECT-TYPE
       SYNTAX      HpSwitchAAAServerGroupEntry
       MAX-ACCESS  not-accessible
       STATUS      current
       DESCRIPTION "RADIUS server group entry."
          INDEX { hpSwitchAAAServerGroupProtocolType,
                  hpSwitchAAAServerGroupIndex,
                  hpSwitchAAAServerGroupServerIndex }
   ::= { hpSwitchAAAServerGroupTable 1 }

    HpSwitchAAAServerGroupEntry ::=
        SEQUENCE {
            hpSwitchAAAServerGroupProtocolType    INTEGER,
            hpSwitchAAAServerGroupIndex           Integer32,
            hpSwitchAAAServerGroupServerIndex     Integer32,
            hpSwitchAAAServerGroupName            DisplayString,
            hpSwitchAAAServerGroupServerInetType  InetAddressType,
            hpSwitchAAAServerGroupServerInetAddr  InetAddress,
            hpSwitchAAAServerGroupStatus          RowStatus,
            hpSwitchAAAServerGroupServerFqdn      DisplayString,
            hpSwitchAAAServerGroupTLSEnable       TruthValue
        }

    hpSwitchAAAServerGroupProtocolType OBJECT-TYPE
        SYNTAX      INTEGER {
                        radius(1),
                        tacacs(2)
                    }
        MAX-ACCESS  not-accessible
        STATUS      current
        DESCRIPTION "This part of the index indicates which protocol
                     server the server group is for.  See the documentation
                     protocols supported."
        ::= { hpSwitchAAAServerGroupEntry 1 }

    hpSwitchAAAServerGroupIndex OBJECT-TYPE
        SYNTAX      Integer32
        MAX-ACCESS  not-accessible
        STATUS      current
        DESCRIPTION "This index indicates the server group in the
                     AAA server group table."
        ::= { hpSwitchAAAServerGroupEntry 2 }

    hpSwitchAAAServerGroupServerIndex OBJECT-TYPE
        SYNTAX      Integer32 
        MAX-ACCESS  not-accessible
        STATUS      current
        DESCRIPTION "The index value which identifies the server in
                     the server group."
        ::= { hpSwitchAAAServerGroupEntry 3 }

    hpSwitchAAAServerGroupName OBJECT-TYPE
        SYNTAX      DisplayString (SIZE(0..255))
        MAX-ACCESS  read-create
        STATUS      current
        DESCRIPTION "The name of a given AAA server group. The current 
                     maximum length is 12."
        ::= { hpSwitchAAAServerGroupEntry 4 }

     hpSwitchAAAServerGroupServerInetType OBJECT-TYPE
         SYNTAX      InetAddressType
         MAX-ACCESS  read-create
         STATUS      current
         DESCRIPTION "The IP Address type of the server.
                      Currently only Ipv4 is supported."
         ::= { hpSwitchAAAServerGroupEntry 5 } 

     hpSwitchAAAServerGroupServerInetAddr OBJECT-TYPE
         SYNTAX      InetAddress
         MAX-ACCESS  read-create
         STATUS      current
         DESCRIPTION "The IP Address of the server."
         ::= { hpSwitchAAAServerGroupEntry 6 } 

     hpSwitchAAAServerGroupStatus OBJECT-TYPE
         SYNTAX      RowStatus
         MAX-ACCESS  read-create
         STATUS      current
         DESCRIPTION "The status of the AAA server group row.
                      Supported values are createAndGo, destroy, and active."
         ::= { hpSwitchAAAServerGroupEntry 7 }

    hpSwitchAAAServerGroupServerFqdn OBJECT-TYPE
       SYNTAX      DisplayString (SIZE (1..255)) 
       MAX-ACCESS  read-create
       STATUS      current
       DESCRIPTION "The FQDN address of RADIUS Server. When the RADIUS server 
                    has been configured with IPv6 address of IPv4 address, 
                    the value of this object will be set to Null."
         ::= { hpSwitchAAAServerGroupEntry 8 }

    hpSwitchAAAServerGroupTLSEnable OBJECT-TYPE
        SYNTAX      TruthValue
        MAX-ACCESS  read-create
        STATUS      current
        DESCRIPTION "This object differentiates whether the RADIUS 
                     server connection is TLS enabled or not.”
                     By default, it is not TLS enabled."
        DEFVAL    {false}
        ::= { hpSwitchAAAServerGroupEntry 9 }
-- ------------------------------------------------------------
-- AAA Server Group NAS-ID Table
-- ------------------------------------------------------------


    hpSwitchAAAServerGroupNasTable OBJECT-TYPE
        SYNTAX      SEQUENCE OF HpSwitchAAAServerGroupNasEntry
        MAX-ACCESS  not-accessible
        STATUS      current
        DESCRIPTION "This table lists the RADIUS server groups with nas-id."
        ::= { hpSwitchAuthenticationMIB 27 }

   hpSwitchAAAServerGroupNasEntry OBJECT-TYPE
       SYNTAX      HpSwitchAAAServerGroupNasEntry
       MAX-ACCESS  not-accessible
       STATUS      current
       DESCRIPTION "RADIUS server group entry."
          INDEX { hpSwitchAAAServerGroupNasProtocolType,
                  hpSwitchAAAServerGroupNasIndex
                   }
   ::= { hpSwitchAAAServerGroupNasTable 1 }

    HpSwitchAAAServerGroupNasEntry ::=
        SEQUENCE {
            hpSwitchAAAServerGroupNasProtocolType    INTEGER,
            hpSwitchAAAServerGroupNasIndex           Integer32,
            hpSwitchAAAServerGroupNasName            DisplayString,
            hpSwitchAAAServerGroupNasId              DisplayString,
            hpSwitchAAAServerGroupNasStatus          RowStatus
        }

     hpSwitchAAAServerGroupNasProtocolType OBJECT-TYPE
        SYNTAX      INTEGER {
                        radius(1),
                        tacacs(2)
                    }
        MAX-ACCESS  not-accessible
        STATUS      current
        DESCRIPTION "This part of the index indicates the protocol
                     type for the server group."
        ::= { hpSwitchAAAServerGroupNasEntry 1 }

    hpSwitchAAAServerGroupNasIndex OBJECT-TYPE
        SYNTAX      Integer32
        MAX-ACCESS  not-accessible
        STATUS      current
        DESCRIPTION "This index indicates the server group in the
                     AAA server group table."
        ::= { hpSwitchAAAServerGroupNasEntry 2 }

    hpSwitchAAAServerGroupNasName OBJECT-TYPE
        SYNTAX      DisplayString (SIZE(0..255))
        MAX-ACCESS  read-create
        STATUS      current
        DESCRIPTION "The name of a given AAA server group. The current 
                     maximum length is 12."
        ::= { hpSwitchAAAServerGroupNasEntry 3 }


    hpSwitchAAAServerGroupNasId OBJECT-TYPE
         SYNTAX      DisplayString (SIZE(0..255))
         MAX-ACCESS  read-create
         STATUS      current
         DESCRIPTION "The NAS-ID for the RADIUS Server group.
                      Maximum length is 32."
         ::= { hpSwitchAAAServerGroupNasEntry 4 } 

     hpSwitchAAAServerGroupNasStatus OBJECT-TYPE
         SYNTAX      RowStatus
         MAX-ACCESS  read-create
         STATUS      current
         DESCRIPTION "The status of the AAA server group row.
                      Supported values are createAndGo, destroy, and active."
         ::= { hpSwitchAAAServerGroupNasEntry 5 }

-- ------------------------------------------------------------
-- Local Management Privilege UserNames Table
-- ------------------------------------------------------------

   hpSwitchLocalMgmtPrivUsernamesTable OBJECT-TYPE
        SYNTAX      SEQUENCE OF HpSwitchLocalMgmtPrivUsernamesEntry
        MAX-ACCESS  not-accessible
        STATUS      current
        DESCRIPTION "This table lists the Local Management
                     Privilege user names."
        ::= { hpSwitchAuthenticationMIB 21 }

   hpSwitchLocalMgmtPrivUsernamesEntry OBJECT-TYPE
        SYNTAX      HpSwitchLocalMgmtPrivUsernamesEntry
        MAX-ACCESS  not-accessible
        STATUS      current
        DESCRIPTION "Local Management Usernames entry."
          INDEX { hpSwitchLocalMgmtPrivUsernameIndex }

        ::= { hpSwitchLocalMgmtPrivUsernamesTable 1 }

   HpSwitchLocalMgmtPrivUsernamesEntry ::=
        SEQUENCE {
            hpSwitchLocalMgmtPrivUsernameIndex         Integer32,
            hpSwitchLocalMgmtPrivUsernameStr           OCTET STRING,
            hpSwitchLocalMgmtPrivUsernamePasswdType    INTEGER,
            hpSwitchLocalMgmtPrivUsernamePasswd        OCTET STRING,
            hpSwitchLocalMgmtPrivUsernameGrpIndex      Integer32,
            hpSwitchLocalMgmtPrivUsernameStatus        RowStatus,
            hpSwitchLocalMgmtPwdUserAgingInterval      Integer32,
            hpSwitchLocalMgmtPwdUserPasswdLengthValue  Integer32,
            hpSwitchLocalMgmtPrivUsernamePasswdSha256  OCTET STRING

        }

   hpSwitchLocalMgmtPrivUsernameIndex OBJECT-TYPE
        SYNTAX      Integer32 
        MAX-ACCESS  not-accessible
        STATUS      current
        DESCRIPTION "The index value uniquely identifies a row
                     in the command table."
        ::= { hpSwitchLocalMgmtPrivUsernamesEntry 1 }

   hpSwitchLocalMgmtPrivUsernameStr OBJECT-TYPE
        SYNTAX      OCTET STRING ( SIZE (1..255))
        MAX-ACCESS  read-create
        STATUS      current
        DESCRIPTION "The username ."
        ::= { hpSwitchLocalMgmtPrivUsernamesEntry 2 }

   hpSwitchLocalMgmtPrivUsernamePasswdType    OBJECT-TYPE
        SYNTAX      INTEGER {
                       unknown(0),
                       sha1(3),
                       sha256(4)
        }       
        MAX-ACCESS  read-create
        STATUS      current
        DESCRIPTION "The type of encryption used for this
                     Conceptual row password object."
        ::= { hpSwitchLocalMgmtPrivUsernamesEntry 3 }

   hpSwitchLocalMgmtPrivUsernamePasswd OBJECT-TYPE
        SYNTAX      OCTET STRING ( SIZE (0..255))
        MAX-ACCESS  read-create
        STATUS      current
        DESCRIPTION "Storage location for the password associated 
                     with this Username.  Always returns a NULL string."
        ::= { hpSwitchLocalMgmtPrivUsernamesEntry 4 }


   hpSwitchLocalMgmtPrivUsernameGrpIndex  OBJECT-TYPE
        SYNTAX      Integer32
        MAX-ACCESS  read-create
        STATUS      current
        DESCRIPTION "The index that represents which group this
                     user is a member of."
        ::= { hpSwitchLocalMgmtPrivUsernamesEntry 5 }

   hpSwitchLocalMgmtPrivUsernameStatus OBJECT-TYPE
        SYNTAX      RowStatus
        MAX-ACCESS  read-create
        STATUS      current
        DESCRIPTION "The status of the  Local Management Privilege
                     username row."
        ::= { hpSwitchLocalMgmtPrivUsernamesEntry 6 }

   hpSwitchLocalMgmtPwdUserAgingInterval   OBJECT-TYPE
        SYNTAX      Integer32 (0..365)
        MAX-ACCESS  read-create
        STATUS      current
        DESCRIPTION "This object holds the user password aging value."
        ::= { hpSwitchLocalMgmtPrivUsernamesEntry 7 }

   hpSwitchLocalMgmtPwdUserPasswdLengthValue   OBJECT-TYPE
        SYNTAX      Integer32 (1..64)
        MAX-ACCESS  read-create
        STATUS      current
        DESCRIPTION "This object holds length of local user password. " 
        DEFVAL      { 8 }
        ::= { hpSwitchLocalMgmtPrivUsernamesEntry 8 }

   hpSwitchLocalMgmtPrivUsernamePasswdSha256 OBJECT-TYPE
        SYNTAX      OCTET STRING ( SIZE (0..255))
        MAX-ACCESS  read-create
        STATUS      current
        DESCRIPTION "Storage location for the sha256 password associated 
                     with this Username.  Always returns a NULL string."
        ::= { hpSwitchLocalMgmtPrivUsernamesEntry 9 }

-- ------------------------------------------------------------
-- Conformance    
-- ------------------------------------------------------------

    hpSwitchAuthenticationMIBConformance
        OBJECT IDENTIFIER ::= { hpSwitchAuthenticationMIB 11 }

    hpSwitchAuthenticationMIBCompliances
        OBJECT IDENTIFIER ::= { hpSwitchAuthenticationMIBConformance 1}

    hpSwitchAuthenticationMIBGroups
        OBJECT IDENTIFIER ::= { hpSwitchAuthenticationMIBConformance 2}


    hpSwitchAuthenticationMIBCompliance MODULE-COMPLIANCE 
        STATUS      deprecated
        DESCRIPTION "The compliance statement for devices implementing the
                     HP Authentication Mib."
        MODULE
            MANDATORY-GROUPS { hpSwitchAuthenticationConfigGroup,
                               hpSwitchTacacsConfigGroup,
                               hpSwitchTacacsStatsGroup }
        ::= { hpSwitchAuthenticationMIBCompliances 1 }

    hpSwitchAuthenticationMIBCompliance1 MODULE-COMPLIANCE 
        STATUS      deprecated 
        DESCRIPTION "The compliance statement for devices implementing the
                     HP Authentication Mib."
        MODULE
            MANDATORY-GROUPS { hpSwitchAuthenticationConfigGroup,
                               hpSwitchTacacsConfigGroup,
                               hpSwitchTacacsStatsGroup,
                               hpSwitchRadiusConfigGroup}
            GROUP   hpSwitchCertStatusGroup2
            DESCRIPTION "A collection of objects for configuring
                         Certificate Status."                   
        ::= { hpSwitchAuthenticationMIBCompliances 2 }

   hpSwitchAuthenticationMIBCompliance2 MODULE-COMPLIANCE
        STATUS      deprecated
        DESCRIPTION "The compliance statement for devices implementing the
                     HP Authentication Mib."
        MODULE
            MANDATORY-GROUPS { hpSwitchAuthenticationConfigGroup1,
                               hpSwitchTacacsConfigGroup,
                               hpSwitchTacacsStatsGroup,
                               hpSwitchRadiusConfigGroup }
            GROUP   hpSwitchKmsGroup
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            ::= { hpSwitchAuthenticationMIBCompliances 3 }

   hpSwitchAuthenticationMIBComplianceOobm MODULE-COMPLIANCE
        STATUS      deprecated 
        DESCRIPTION "The compliance statement for devices implementing the
                     HP Authentication Mib with OOBM support"
        MODULE

            GROUP   hpSwitchRadiusOobmGroup
            DESCRIPTION "A collection of objects for configuring
                         Radius with OOBM."

            GROUP   hpSwitchTacacsOobmGroup
            DESCRIPTION "A collection of objects for configuring
                         Tacacs with OOBM."

        ::= { hpSwitchAuthenticationMIBCompliances 4 }

-- ------------------------------------------------------------
-- RIP Interface authentication configuration table
-- ------------------------------------------------------------

    hpSwitchRipIfAuthTable OBJECT-TYPE
         SYNTAX      SEQUENCE OF HpSwitchRipIfAuthEntry
         MAX-ACCESS  not-accessible
         STATUS      current
         DESCRIPTION "This table supplements the RIP interface
                      configuration table."
    ::= { hpSwitchAuthenticationMIB 23 }

    hpSwitchRipIfAuthEntry OBJECT-TYPE
         SYNTAX      HpSwitchRipIfAuthEntry
         MAX-ACCESS  not-accessible
         STATUS      current
         DESCRIPTION "RIP interface authentication
                      configuration table entry."
         AUGMENTS { rip2IfConfEntry }
    ::= { hpSwitchRipIfAuthTable 1 }

    HpSwitchRipIfAuthEntry ::=
         SEQUENCE {
            hpSwitchRipIfAuthChain DisplayString,
            hpSwitchRip2IfConfAuthKeyEncrypted OCTET STRING
         }

    hpSwitchRipIfAuthChain OBJECT-TYPE
         SYNTAX      DisplayString (SIZE(0..32))
         MAX-ACCESS  read-create
         STATUS      current
         DESCRIPTION "This object configures the KMS chain name for
                      RIP interfaces."
    ::= { hpSwitchRipIfAuthEntry 1 }

    hpSwitchRip2IfConfAuthKeyEncrypted OBJECT-TYPE
         SYNTAX      OCTET STRING (SIZE(0..256))
         MAX-ACCESS  read-create
         STATUS      current
         DESCRIPTION "This object represents the encrypted format of the
                      authentication key stored in the object rip2IfConfAuthKey.
                      This object may only be read or written when
                      hpSwitchAuthenticationEncryptCredentialsMethod is set to a
                      value other than none(0). This object should only be
                      written with an encrypted key."
   ::= { hpSwitchRipIfAuthEntry 2 }

-- ------------------------------------------------------------
-- Notifications
-- ------------------------------------------------------------
   hpSwitchAuthNotifications  
        OBJECT IDENTIFIER ::= { hpSwitchAuthenticationMIB 0 }

   hpSwitchPasswordExpiryNotify NOTIFICATION-TYPE
        OBJECTS { 
           hpicfSwitchUserName  -- The user-name for which password has expired
           }
        STATUS       current
        DESCRIPTION "An hpSwitchPasswordExpiryNotify notification that signifies that 
                     the password configured for the specified user has expired."
        ::= { hpSwitchAuthNotifications 1 }

-- ------------------------------------------------------------
-- Compliances
-- ------------------------------------------------------------

    hpSwitchUserConfigMIBCompliance MODULE-COMPLIANCE
        STATUS      deprecated
        DESCRIPTION "The compliance statement for configuring user-name/password
                     for operator/manager/port-access."
        MODULE

            GROUP    hpSwitchUserConfigGroup
            DESCRIPTION "A collection of objects for configuring user-name/password
                        for operator/manager/port-access."
        ::= { hpSwitchAuthenticationMIBCompliances 5 }

    hpSwitchAAAServerMIBCompliance MODULE-COMPLIANCE
        STATUS      deprecated
        DESCRIPTION "The compliance statement for configuring RADIUS server groups."
        MODULE
            
            GROUP   hpSwitchAAAServerGroup
            DESCRIPTION "A collection of objects for configuring RADIUS server groups."
       ::= { hpSwitchAuthenticationMIBCompliances 6 }  

   hpSwitchAuthenMIBCompliance      MODULE-COMPLIANCE
        STATUS      current
        DESCRIPTION "The compliance statement for listing the authentication methods
                    to be tried for granting different access levels through
                    various access tasks"
        MODULE
            
            GROUP   hpSwitchAuthenGroup
            DESCRIPTION "A collection of objects for listing the authentication methods
                         to be tried for granting different access levels through
                         various access tasks"
       ::= { hpSwitchAuthenticationMIBCompliances 7 }  
                  

   hpSwitchLocalMgmtPrivUserMIBCompliance      MODULE-COMPLIANCE
        STATUS      deprecated
        DESCRIPTION "The compliance statement for listing the
                     local management privilege methods to be
                     tried for granting
                     different access levels through
                     various access tasks"
        MODULE
            
        GROUP   hpSwitchAuthLocalMgmtPrivUserGroup
        DESCRIPTION "A collection of objects for listing the
                     local management privilege methods to be tried 
                     for granting different access levels through
                     various access tasks"

        OBJECT  hpSwitchLocalMgmtPrivUsernameStr
        MIN-ACCESS  read-only
        DESCRIPTION
            "Write access is not required."
        OBJECT  hpSwitchLocalMgmtPrivUsernamePasswdType
        MIN-ACCESS  read-only
        DESCRIPTION
            "Write access is not required."
        OBJECT  hpSwitchLocalMgmtPrivUsernamePasswd
        MIN-ACCESS  read-only
        DESCRIPTION
            "Write access is not required."
        OBJECT  hpSwitchLocalMgmtPrivUsernameGrpIndex
        MIN-ACCESS  read-only
        DESCRIPTION
            "Write access is not required."

       ::= { hpSwitchAuthenticationMIBCompliances 8 }  
                           
   hpSwitchAuthenticationMIBCompliance3 MODULE-COMPLIANCE
        STATUS      deprecated
        DESCRIPTION "The compliance statement for devices implementing the
                     HP Authentication Mib."
        MODULE
            MANDATORY-GROUPS { hpSwitchAuthenticationConfigGroup1,
                               hpSwitchTacacsConfigGroup1,
                               hpSwitchTacacsStatsGroup,
                               hpSwitchRadiusConfigGroup1 }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            ::= { hpSwitchAuthenticationMIBCompliances 9 }

    hpSwitchUserConfigMIBCompliance1 MODULE-COMPLIANCE
        STATUS      deprecated
        DESCRIPTION "The compliance statement for configuring user-name/password
                     for operator/manager/port-access."
        MODULE

            GROUP    hpSwitchUserConfigGroup1
            DESCRIPTION "A collection of objects for configuring user-name/password
                        for operator/manager/port-access."
        ::= { hpSwitchAuthenticationMIBCompliances 10 }

    hpSwitchLocalMgmtPrivUserMIBCompliance1 MODULE-COMPLIANCE
        STATUS      current
        DESCRIPTION "The compliance statement for configuring user-name/password
                     for operator/manager/port-access."
        MODULE

        GROUP       hpSwitchAuthLocalMgmtPrivUserGroup1
        DESCRIPTION "Row Status of objects for configuring
                     Local Manangement Priviledge Groups"
        ::= { hpSwitchAuthenticationMIBCompliances 11 }

    hpSwitchAuthenticationMIBCompliance4 MODULE-COMPLIANCE
        STATUS      deprecated
        DESCRIPTION "The compliance statement for devices implementing the
                     HP Authentication MIB."
        MODULE       

        GROUP       hpSwitchCertStatusGroup3      
        DESCRIPTION "Collection of objects for configuring
                     Key Certificate"
        ::= { hpSwitchAuthenticationMIBCompliances 12 }

   hpSwitchAuthenticationMIBCompliance5 MODULE-COMPLIANCE
        STATUS     deprecated 
        DESCRIPTION "The compliance statement for devices implementing the
                     HP Authentication Mib."
        MODULE
            MANDATORY-GROUPS { hpSwitchAuthenticationConfigGroup2,
                               hpSwitchTacacsConfigGroup1,
                               hpSwitchTacacsStatsGroup,
                               hpSwitchRadiusConfigGroup1 }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            ::= { hpSwitchAuthenticationMIBCompliances 13 }

   hpSwitchAuthenticationMIBComplianceOobm1 MODULE-COMPLIANCE
        STATUS      deprecated
        DESCRIPTION "The compliance statement for devices implementing the
                     HP Authentication Mib with OOBM support"
        MODULE

            GROUP   hpSwitchTacacsOobmGroup
            DESCRIPTION "A collection of objects for configuring
                         Tacacs with OOBM."

        ::= { hpSwitchAuthenticationMIBCompliances 14 }

   hpSwitchAuthenticationMIBCompliance6 MODULE-COMPLIANCE
        STATUS      deprecated
        DESCRIPTION "The compliance statement for devices implementing the
                     HP Authentication Mib."
        MODULE
            MANDATORY-GROUPS { hpSwitchAuthenticationConfigGroup2,
                               hpSwitchTacacsConfigGroup1,
                               hpSwitchTacacsStatsGroup,
                               hpSwitchRadiusConfigGroup2 }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            ::= { hpSwitchAuthenticationMIBCompliances 15 }
   
   hpSwitchAuthenticationMIBCompliance7 MODULE-COMPLIANCE
        STATUS      deprecated
        DESCRIPTION "The compliance statement for devices implementing the
                     HP Authentication Mib."
        MODULE
            MANDATORY-GROUPS { hpSwitchAuthenticationConfigGroup3,
                               hpSwitchTacacsConfigGroup1,
                               hpSwitchTacacsStatsGroup,
                               hpSwitchRadiusConfigGroup2 }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            ::= { hpSwitchAuthenticationMIBCompliances 16 }

    hpSwitchAuthenticationMIBCompliance8 MODULE-COMPLIANCE
        STATUS      current
        DESCRIPTION "The compliance statement for devices implementing the
                     HP Authentication Mib."
        MODULE

            GROUP   hpSwitchAuthenticationConfigGroup4
            DESCRIPTION "A collection of objects which controls bypassing of
                         the username during authentication to get Operator
                         or Manager access."
            ::= { hpSwitchAuthenticationMIBCompliances 17 }

   hpSwitchAuthenticationMIBCompliance9 MODULE-COMPLIANCE
        STATUS      deprecated
        DESCRIPTION "The compliance statement for devices implementing the
                     HP Authentication Mib."
        MODULE
            MANDATORY-GROUPS { hpSwitchAuthenticationConfigGroup3,
                               hpSwitchTacacsConfigGroup1,
                               hpSwitchTacacsStatsGroup,
                               hpSwitchRadiusConfigGroup3                                }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup
            DESCRIPTION "A collection of objects for configuring
                     RIP authentication."
	    
            ::= { hpSwitchAuthenticationMIBCompliances 18 }

    hpSwitchAuthenticationMIBCompliance10 MODULE-COMPLIANCE
        STATUS      current
        DESCRIPTION "The compliance statement for devices implementing the
                     HP password Authentication MIB."
        MODULE

            GROUP   hpSwitchAuthenticationPasswordConfigGroup
            DESCRIPTION "A collection of objects for configuration 
                         password as per UCR guideline."
            
            GROUP       hpSwitchAuthNotificationGroup
            DESCRIPTION "A collection of objects that lists the notifications 
                         that are required for password configuration."

            ::= { hpSwitchAuthenticationMIBCompliances 19 }

   hpSwitchLocalMgmtPrivUserMIBCompliance2      MODULE-COMPLIANCE
        STATUS      deprecated
        DESCRIPTION "The compliance statement for listing the
                     local management privilege methods to be
                     tried for granting
                     different access levels through
                     various access tasks"
        MODULE
            
        GROUP   hpSwitchAuthLocalMgmtPrivUserGroup2
        DESCRIPTION "A collection of objects for listing the
                     local management privilege methods to be tried 
                     for granting different access levels through
                     various access tasks"

        OBJECT  hpSwitchLocalMgmtPrivUsernameStr
        MIN-ACCESS  read-only
        DESCRIPTION
            "Write access is not required."
        OBJECT  hpSwitchLocalMgmtPrivUsernamePasswdType
        MIN-ACCESS  read-only
        DESCRIPTION
            "Write access is not required."
        OBJECT  hpSwitchLocalMgmtPrivUsernamePasswd
        MIN-ACCESS  read-only
        DESCRIPTION
            "Write access is not required."
        OBJECT  hpSwitchLocalMgmtPrivUsernameGrpIndex
        MIN-ACCESS  read-only
        DESCRIPTION
            "Write access is not required."

       ::= { hpSwitchAuthenticationMIBCompliances 20 }  

    hpSwitchUserConfigMIBCompliance2 MODULE-COMPLIANCE
        STATUS      deprecated
        DESCRIPTION "The compliance statement for configuring user-name/password
                     for operator/manager/port-access."
        MODULE

            GROUP    hpSwitchUserConfigGroup2
            DESCRIPTION "A collection of objects for configuring user-name/password
                        for operator/manager/port-access."
        ::= { hpSwitchAuthenticationMIBCompliances 21 }

   hpSwitchAuthenticationMIBCompliance11 MODULE-COMPLIANCE
        STATUS      deprecated
        DESCRIPTION "The compliance statement for devices implementing the
                     HP Authentication Mib."
        MODULE
            MANDATORY-GROUPS { hpSwitchAuthenticationConfigGroup3,
                               hpSwitchTacacsConfigGroup1,
                               hpSwitchTacacsStatsGroup,
                               hpSwitchRadiusConfigGroup4 }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup
            DESCRIPTION "A collection of objects for configuring
                     RIP authentication."
	    
            ::= { hpSwitchAuthenticationMIBCompliances 22 }


   hpSwitchAuthenticationMIBCompliance12 MODULE-COMPLIANCE
        STATUS      deprecated
        DESCRIPTION "The compliance statement for devices implementing the
                     HP Authentication Mib."
        MODULE
            MANDATORY-GROUPS { hpSwitchTacacsConfigGroup1,
                               hpSwitchTacacsStatsGroup,
                               hpSwitchRadiusConfigGroup4,
                               hpSwitchAuthenticationConfigGroup5 }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup
            DESCRIPTION "A collection of objects for configuring
                     RIP authentication."
            ::= { hpSwitchAuthenticationMIBCompliances 23 }


    hpSwitchUserConfigMIBCompliance3 MODULE-COMPLIANCE
        STATUS      current
        DESCRIPTION "The compliance statement for configuring username and password
                     for operator, manager or port-access."
        MODULE

            GROUP    hpSwitchUserConfigGroup3
            DESCRIPTION "A collection of objects for configuring username and
                        password for operator, manager or port-access."
        ::= { hpSwitchAuthenticationMIBCompliances 24 }

   hpSwitchLocalMgmtPrivUserMIBCompliance3      MODULE-COMPLIANCE
        STATUS      current
        DESCRIPTION "The compliance statement for listing the
                     local management privilege methods to be
                     tried for granting
                     different access levels through
                     various access tasks"
        MODULE
            
        GROUP   hpSwitchAuthLocalMgmtPrivUserGroup3
        DESCRIPTION "A collection of objects for listing the
                     local management privilege methods to be tried 
                     for granting different access levels through
                     various access tasks"

        OBJECT  hpSwitchLocalMgmtPrivUsernameStr
        MIN-ACCESS  read-only
        DESCRIPTION
            "Write access is not required."
        OBJECT  hpSwitchLocalMgmtPrivUsernamePasswdType
        MIN-ACCESS  read-only
        DESCRIPTION
            "Write access is not required."
        OBJECT  hpSwitchLocalMgmtPrivUsernamePasswd
        MIN-ACCESS  read-only
        DESCRIPTION
            "Write access is not required."
        OBJECT  hpSwitchLocalMgmtPrivUsernameGrpIndex
        MIN-ACCESS  read-only
        DESCRIPTION
            "Write access is not required."

       ::= { hpSwitchAuthenticationMIBCompliances 25 }  


   hpSwitchAuthenticationMIBCompliance13 MODULE-COMPLIANCE
        STATUS      deprecated
        DESCRIPTION "The compliance statement for devices implementing the
                     HP Authentication Mib."
        MODULE
            MANDATORY-GROUPS { hpSwitchTacacsConfigGroup1,
                               hpSwitchTacacsStatsGroup,
                               hpSwitchRadiusConfigGroup4,
                               hpSwitchAuthenticationConfigGroup5 }
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 26 }

     hpSwitchAuthenticationMIBCompliance14 MODULE-COMPLIANCE
        STATUS      deprecated
        DESCRIPTION "The compliance statement for devices implementing the
                     HP Authentication Mib."
        MODULE
            MANDATORY-GROUPS { hpSwitchTacacsConfigGroup1,
                               hpSwitchTacacsStatsGroup,
                               hpSwitchRadiusConfigGroup4,
                               hpSwitchAuthenticationConfigGroup6 }
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 27 }

     hpSwitchAuthenticationMIBCompliance15 MODULE-COMPLIANCE
        STATUS      deprecated
        DESCRIPTION "The compliance statement for devices implementing the
                     HP Authentication Mib."
        MODULE
            MANDATORY-GROUPS { hpSwitchTacacsConfigGroup1,
                               hpSwitchTacacsStatsGroup,
                               hpSwitchRadiusConfigGroup4,
                               hpSwitchAuthenticationConfigGroup7}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 28 }
   
    hpSwitchAuthenticationMIBCompliance16 MODULE-COMPLIANCE
        STATUS      deprecated
        DESCRIPTION "The compliance statement for devices implementing the
                     HP Authentication Mib."
        MODULE
            MANDATORY-GROUPS { hpSwitchTacacsConfigGroup1,
                               hpSwitchTacacsStatsGroup,
                               hpSwitchRadiusConfigGroup5,
                               hpSwitchAuthenticationConfigGroup7}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 29 }

    hpSwitchFrontPanelSecurityCompliance MODULE-COMPLIANCE
        STATUS      current
        DESCRIPTION "The compliance statement for configuring front
                     panel security commands."
        MODULE

            GROUP    hpSwitchFrontPanelSecurityGroup
            DESCRIPTION "A collection of objects for configuring front
                        panel security commands."
            ::= { hpSwitchAuthenticationMIBCompliances 30 }

hpSwitchAuthenticationMIBCompliance17 MODULE-COMPLIANCE
        STATUS      deprecated
        DESCRIPTION "The compliance statement for devices implementing the
                     HP Authentication Mib."
        MODULE
            MANDATORY-GROUPS { hpSwitchTacacsConfigGroup1,
                               hpSwitchTacacsStatsGroup,
                               hpSwitchRadiusConfigGroup6,
                               hpSwitchAuthenticationConfigGroup8}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 31 }
    
hpSwitchAuthenticationMIBCompliance18 MODULE-COMPLIANCE
        STATUS      deprecated
        DESCRIPTION "The compliance statement for devices implementing the
                     HP Authentication Mib."
        MODULE
            MANDATORY-GROUPS { hpSwitchTacacsConfigGroup1,
                               hpSwitchTacacsStatsGroup,
                               hpSwitchRadiusConfigGroup7,
                               hpSwitchAuthenticationConfigGroup9}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 32 }

hpSwitchAuthenticationMIBCompliance19 MODULE-COMPLIANCE
        STATUS      deprecated
        DESCRIPTION "The compliance statement for devices implementing the
                     HP Authentication Mib."
        MODULE
            MANDATORY-GROUPS { hpSwitchTacacsConfigGroup2,
                               hpSwitchTacacsStatsGroup1,
                               hpSwitchRadiusConfigGroup7,
                               hpSwitchAuthenticationConfigGroup9}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 33 }

   hpSwitchAuthenticationMIBComplianceOobm2 MODULE-COMPLIANCE
        STATUS      current
        DESCRIPTION "The compliance statement for devices implementing the
                     HP Authentication Mib with OOBM support"
        MODULE

            GROUP   hpSwitchTacacsOobmGroup1
            DESCRIPTION "A collection of objects for configuring
                         TACACS+ with OOBM."

        ::= { hpSwitchAuthenticationMIBCompliances 34 }

hpSwitchAuthenticationMIBCompliance20 MODULE-COMPLIANCE
        STATUS      deprecated
        DESCRIPTION "The compliance statement for devices implementing the
                     HP Authentication Mib."
        MODULE
            MANDATORY-GROUPS { hpSwitchTacacsConfigGroup2,
                               hpSwitchTacacsStatsGroup1,
                               hpSwitchRadiusConfigGroup8,
                               hpSwitchAuthenticationConfigGroup9}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 35 }

hpSwitchAuthenticationMIBCompliance21 MODULE-COMPLIANCE
        STATUS      deprecated
        DESCRIPTION "The compliance statement for devices implementing the
                     HP Authentication Mib."
        MODULE
            MANDATORY-GROUPS { hpSwitchTacacsConfigGroup2,
                               hpSwitchTacacsStatsGroup1,
                               hpSwitchRadiusConfigGroup9,
                               hpSwitchAuthenticationConfigGroup9}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 37 }

hpSwitchAuthenticationMIBCompliance22 MODULE-COMPLIANCE
        STATUS      deprecated
        DESCRIPTION "The compliance statement for devices implementing the
                     HP Authentication Mib."
        MODULE
            MANDATORY-GROUPS { hpSwitchTacacsConfigGroup2,
                               hpSwitchTacacsStatsGroup1,
                               hpSwitchRadiusConfigGroup10,
                               hpSwitchAuthenticationConfigGroup9}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 38 }

hpSwitchAuthenticationMIBCompliance23 MODULE-COMPLIANCE
        STATUS      deprecated
        DESCRIPTION "The compliance statement for devices implementing the
                     HP Authentication Mib."
        MODULE
            MANDATORY-GROUPS { hpSwitchTacacsConfigGroup2,
                               hpSwitchTacacsStatsGroup1,
                               hpSwitchRadiusConfigGroup11,
                               hpSwitchAuthenticationConfigGroup9}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 39 }
   
    hpSwitchAuthenticationMIBCompliance26 MODULE-COMPLIANCE
        STATUS      deprecated
        DESCRIPTION "The compliance statement for devices implementing the
                     HP Authentication Mib."
        MODULE
            MANDATORY-GROUPS { hpSwitchTacacsConfigGroup3,
                               hpSwitchTacacsStatsGroup1,
                               hpSwitchRadiusConfigGroup10,
                               hpSwitchAuthenticationConfigGroup9}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 42 }

     hpSwitchAuthenticationMIBCompliance27 MODULE-COMPLIANCE
        STATUS      current
        DESCRIPTION "The compliance statement for devices implementing the
                     HP Authentication Mib."
        MODULE
            MANDATORY-GROUPS { hpSwitchTacacsConfigGroup3,
                               hpSwitchTacacsStatsGroup1,
                               hpSwitchRadiusConfigGroup12}
            GROUP   hpSwitchKmsGroup1
            DESCRIPTION "A collection of objects for configuring
                         KMS functionality."
            GROUP   hpSwitchOspfAuthGroup1
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            GROUP   hpSwitchRipAuthGroup1
            DESCRIPTION "A collection of objects for configuring
                     RIP authentication."
            ::= { hpSwitchAuthenticationMIBCompliances 43 }

    hpSwitchAAAServerMIBCompliance2 MODULE-COMPLIANCE
        STATUS      current
        DESCRIPTION "The compliance statement for configuring RADIUS server groups."
        MODULE

            GROUP   hpSwitchAAAServerGroup2
            DESCRIPTION "A collection of objects for configuring RADIUS server groups."
       ::= { hpSwitchAuthenticationMIBCompliances 44 }
	   
--
-- GROUPS
--

   hpSwitchAuthenticationConfigGroup OBJECT-GROUP
        OBJECTS     { hpSwitchNumLoginAttempts,
                      hpSwitchAuthenLoginPrimary,
                      hpSwitchAuthenLoginSecondary,
                      hpSwitchAuthenEnablePrimary,
                      hpSwitchAuthenEnableSecondary
                    }
        STATUS      deprecated 
        DESCRIPTION "A collection of objects for configuring the
                    authentication features."
        ::= { hpSwitchAuthenticationMIBGroups 1 }

    hpSwitchTacacsConfigGroup OBJECT-GROUP
        OBJECTS     { hpSwitchTacacsTimeout,
                      hpSwitchTacacsAuthKey,
                      hpSwitchTacacsServerIpAddr,
                      hpSwitchTacacsServerKey,
                      hpSwitchTacacsServerStatus,
                      hpSwitchTacacsDeadTime
                    }
        STATUS      deprecated
        DESCRIPTION "A collection of objects for configuring the 
                    state of the TACACS+ protocol."
        ::= { hpSwitchAuthenticationMIBGroups 2 }

    hpSwitchTacacsStatsGroup OBJECT-GROUP
        OBJECTS     { hpTacacsStatsTacacsServerIpAddr,
                      hpTacacsStatsNumSessOpened,
                      hpTacacsStatsNumSessClosed,
                      hpTacacsStatsNumSessAborted,
                      hpTacacsStatsNumSessErrors,
                      hpTacacsStatsNumPktsIn,
                      hpTacacsStatsNumPktsOut,
                      hpTacacsStatsNumAuthPktsIn,
                      hpTacacsStatsNumAuthPktsOut,
                      hpTacacsStatsNumAuthPktsTimedOut,
                      hpTacacsStatsNumAutzPktsIn,
                      hpTacacsStatsNumAutzPktsOut,
                      hpTacacsStatsNumAutzPktsTimedOut,
                      hpTacacsStatsNumAcctPktsIn,
                      hpTacacsStatsNumAcctPktsOut,
                      hpTacacsStatsNumAcctPktsTimedOut
                    }
        STATUS      deprecated
        DESCRIPTION "A collection of objects for viewing the
                    status information of the TACACS+ protocol."
        ::= { hpSwitchAuthenticationMIBGroups 3 }

    hpSwitchRadiusConfigGroup OBJECT-GROUP
        OBJECTS     { hpSwitchRadiusDeadTime,
                      hpSwitchRadiusTimeout,
                      hpSwitchRadiusRetransmitAttempts,
                      hpSwitchRadiusAuthKey,
                      hpSwitchRadiusDynAutzPortNumber,
                      hpSwitchRadiusServerIpAddr,
                      hpSwitchRadiusServerKey,
                      hpSwitchRadiusServerAuthPortNumber,
                      hpSwitchRadiusServerAcctPortNumber,
                      hpSwitchRadiusServerDynAutzEnabled,
                      hpSwitchRadiusServerDynAutzTimeWindow,
                      hpSwitchRadiusServerStatus
                    }
        STATUS      deprecated
        DESCRIPTION "A collection of objects for configuring the 
                    state of the RADIUS protocol."
        ::= { hpSwitchAuthenticationMIBGroups 4 }

    hpSwitchKmsGroup OBJECT-GROUP
        OBJECTS     { hpSwitchKmsChainName,
                      hpSwitchKmsChainKeys,
                      hpSwitchKmsChainActiveKeys,
                      hpSwitchKmsChainExpKeys,
                      hpSwitchKmsChainStatus,
                      hpSwitchKmsKeyStr,
                      hpSwitchKmsKeyStartTime,
                      hpSwitchKmsKeyStopTime,
                      hpSwitchKmsKeyTxStartTime,
                      hpSwitchKmsKeyTxStopTime,
                      hpSwitchKmsChainStatus,
                      hpSwitchKmsKeyStatus
                    }
        STATUS      deprecated
        DESCRIPTION "A collection of objects for configuring
                     KMS functionality."
        ::= { hpSwitchAuthenticationMIBGroups 6 }        

    hpSwitchOspfAuthGroup OBJECT-GROUP
        OBJECTS     { hpSwitchOspfVirtIfAuthChain,
                      hpSwitchOspfIfAuthChain
                    }
        STATUS      deprecated
        DESCRIPTION "A collection of objects for configuring
                     OSPF authentication."
        ::= { hpSwitchAuthenticationMIBGroups 7 }        

    hpSwitchAuthenticationConfigGroup1 OBJECT-GROUP
        OBJECTS     { hpSwitchNumLoginAttempts,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod
                    }
        STATUS      deprecated
        DESCRIPTION "A collection of objects for configuring the
                    authentication features."
        ::= { hpSwitchAuthenticationMIBGroups 8 }

    hpSwitchSslGroup  OBJECT-GROUP
        OBJECTS     { hpSwitchSslAdminStatus,
                      hpSwitchSslPortNumber
                    }
        STATUS      current
        DESCRIPTION "A collection of objects for configuring SSL
                    Servers."
        ::= { hpSwitchAuthenticationMIBGroups 9 }

    hpSwitchCertGroup   OBJECT-GROUP
        OBJECTS     { hpSwitchServerCertificateType,
                      hpSwitchServerCertificateRSAKeySize,
                      hpSwitchServerCertificateSerialNumber,
                      hpSwitchServerCertificateStartDate,
                      hpSwitchServerCertificateEndDate,
                      hpSwitchServerCertificateCommonName,
                      hpSwitchServerCertificateOrgUnit,
                      hpSwitchServerCertificateOrgName,
                      hpSwitchServerCertificateCityName,
                      hpSwitchServerCertificateStateName,
                      hpSwitchServerCertificateCountryCode,
                      hpSwitchServerCertificateFingerprintMD5,
                      hpSwitchServerCertificateFingerprintSHA1
                    }
        STATUS      current
        DESCRIPTION "A collection of objects for configuring Certificates."
        ::= { hpSwitchAuthenticationMIBGroups 10 }

    hpSwitchCertStatusGroup  OBJECT-GROUP
        OBJECTS   { hpSwitchServerCertificateOperation,
                    hpSwitchServerNewRSAKeyOperation,
                    hpSwitchServerNewCertificateStartDate,
                    hpSwitchServerNewCertificateEndDate,
                    hpSwitchServerNewCertCommonName,
                    hpSwitchServerNewCertOrgUnit,
                    hpSwitchServerNewCertOrgName,
                    hpSwitchServerNewCertCityName,
                    hpSwitchServerNewCertStateName,
                    hpSwitchServerNewCertificateCountryCode
                  }
        STATUS    current
        DESCRIPTION "A collection of objects for configuring Certificate Status."
       ::= { hpSwitchAuthenticationMIBGroups 11 }

    hpSwitchTacacsOobmGroup OBJECT-GROUP
        OBJECTS     { hpSwitchTacacsServerIpAddr,
                      hpSwitchTacacsServerIsOobm                     
                    }
        STATUS      deprecated
        DESCRIPTION "A collection of objects for configuring the 
                    TACACS+ server entry with support for OOBM 
                    (Out of Band Management) interface."
        ::= { hpSwitchAuthenticationMIBGroups 12 }

    hpSwitchRadiusOobmGroup OBJECT-GROUP
        OBJECTS     { hpSwitchRadiusServerIpAddr,
                      hpSwitchRadiusServerIsOobm
                    }
        STATUS     deprecated 
        DESCRIPTION "A collection of objects for configuring the 
                    RADIUS server entry with support for OOBM 
                    (Out of Band Management) interface."
        ::= { hpSwitchAuthenticationMIBGroups 13 }

    hpSwitchCertStatusGroup2  OBJECT-GROUP
        OBJECTS   { hpSwitchServerNewCertificateCommonName,
                    hpSwitchServerNewCertificateOrgUnit,
                    hpSwitchServerNewCertificateOrgName,
                    hpSwitchServerNewCertificateCityName,
                    hpSwitchServerNewCertificateStateName
                  }
        STATUS    deprecated
        DESCRIPTION "A collection of objects for configuring Certificate Status."
       ::= { hpSwitchAuthenticationMIBGroups 14 }

    hpSwitchUserConfigGroup OBJECT-GROUP
        OBJECTS   { hpicfSwitchUserName,
                    hpicfSwitchOperatorName,
                    hpicfSwitchPortAccessName,
                    hpicfSwitchUserPassword,
                    hpicfSwitchOperatorPassword,
                    hpicfSwitchPortAccessPassword,
                    hpicfSwitchUserPasswordHashType,
                    hpicfSwitchOperatorPasswordHashType,
                    hpicfSwitchPortAccessPasswordHashType,
                    hpicfSwitchUserConfigStatus
                  }
        STATUS    deprecated
        DESCRIPTION "A collection of objects for configuring user-name/password 
                     for operator/manager/port-access."
       ::= { hpSwitchAuthenticationMIBGroups 15 }

    hpSwitchAAAServerGroup   OBJECT-GROUP
        OBJECTS   { hpSwitchAAAServerGroupName,
                    hpSwitchAAAServerGroupServerInetType,
                    hpSwitchAAAServerGroupServerInetAddr,
                    hpSwitchAAAServerGroupStatus,
                    hpSwitchAAAServerGroupServerFqdn
                  }
        STATUS    deprecated
        DESCRIPTION "A collection of objects for configuring RADIUS server groups."
       ::= { hpSwitchAuthenticationMIBGroups 16 }
       
   hpSwitchAuthenGroup      OBJECT-GROUP
       OBJECTS    { hpSwitchAuthenLoginServerGroupName,
                    hpSwitchAuthenEnableServerGroupName,
                    hpSwitchAuthenLoginTwoFactorType,
                    hpSwitchAuthenEnableTwoFactorType,  
                    hpSwitchAuthenLoginSecondAuthMethod,
                    hpSwitchAuthenEnableSecondAuthMethod
                  }  
       STATUS    current
       DESCRIPTION "A collection of objects for listing the authentication methods
                    to be tried for granting different access levels through
                    various access tasks."
       ::= { hpSwitchAuthenticationMIBGroups 17 }

                      
    hpSwitchAuthLocalMgmtPrivUserGroup OBJECT-GROUP
        OBJECTS   { 
            hpSwitchLocalMgmtPrivUsernameStr,
            hpSwitchLocalMgmtPrivUsernamePasswdType,
            hpSwitchLocalMgmtPrivUsernamePasswd,
            hpSwitchLocalMgmtPrivUsernameGrpIndex
        }
        STATUS    deprecated
        DESCRIPTION "A collection of objects for configuring
                     Local Management Privilege Groups"
       ::= { hpSwitchAuthenticationMIBGroups 18 }

    hpSwitchAuthLocalMgmtPrivUserGroup2 OBJECT-GROUP
        OBJECTS   {
            hpSwitchLocalMgmtPrivUsernameStr,
            hpSwitchLocalMgmtPrivUsernamePasswdType,
            hpSwitchLocalMgmtPrivUsernamePasswd,
            hpSwitchLocalMgmtPrivUsernameGrpIndex,
            hpSwitchLocalMgmtPwdUserAgingInterval,
            hpSwitchLocalMgmtPwdUserPasswdLengthValue
        }
        STATUS    deprecated
        DESCRIPTION "A collection of objects for configuring
                     Local Management Privilege Groups"
       ::= { hpSwitchAuthenticationMIBGroups 34 }

    hpSwitchTacacsConfigGroup1 OBJECT-GROUP
        OBJECTS     { hpSwitchTacacsTimeout,
                      hpSwitchTacacsAuthKey,
                      hpSwitchTacacsAuthKeyEncrypted,
                      hpSwitchTacacsServerIpAddr,
                      hpSwitchTacacsServerKey,
                      hpSwitchTacacsServerKeyEncrypted,
                      hpSwitchTacacsServerStatus,
                      hpSwitchTacacsDeadTime
                    }
        STATUS      deprecated
        DESCRIPTION "A collection of objects for configuring the
                    state of the TACACS+ protocol."
        ::= { hpSwitchAuthenticationMIBGroups 19 }

    hpSwitchRadiusConfigGroup1 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerIpAddr,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerStatus
                    }
        STATUS      deprecated 
        DESCRIPTION "A collection of objects for configuring the 
                    state of the RADIUS protocol."
        ::= { hpSwitchAuthenticationMIBGroups 20 }

    hpSwitchKmsGroup1 OBJECT-GROUP
        OBJECTS     { hpSwitchKmsChainName,
                      hpSwitchKmsChainKeys,
                      hpSwitchKmsChainActiveKeys,
                      hpSwitchKmsChainExpKeys,
                      hpSwitchKmsChainStatus,
                      hpSwitchKmsKeyStr,
                      hpSwitchKmsKeyEncrypted,
                      hpSwitchKmsKeyStartTime,
                      hpSwitchKmsKeyStopTime,
                      hpSwitchKmsKeyTxStartTime,
                      hpSwitchKmsKeyTxStopTime,
                      hpSwitchKmsChainStatus,
                      hpSwitchKmsKeyStatus
                    }
        STATUS      current
        DESCRIPTION "A collection of objects for configuring
                     KMS functionality."
        ::= { hpSwitchAuthenticationMIBGroups 21 }

    hpSwitchUserConfigGroup1 OBJECT-GROUP
        OBJECTS   { hpicfSwitchUserName,
                    hpicfSwitchOperatorName,
                    hpicfSwitchPortAccessName,
                    hpicfSwitchUserPassword,
                    hpicfSwitchOperatorPassword,
                    hpicfSwitchPortAccessPassword,
                    hpicfSwitchUserPasswordEncrypted,
                    hpicfSwitchOperatorPasswordEncrypted,
                    hpicfSwitchPortAccessPasswordEncrypted,
                    hpicfSwitchUserPasswordHashType,
                    hpicfSwitchOperatorPasswordHashType,
                    hpicfSwitchPortAccessPasswordHashType,
                    hpicfSwitchUserConfigStatus
                  }
        STATUS    deprecated
        DESCRIPTION "A collection of objects for configuring user-name/password 
                     for operator/manager/port-access."
       ::= { hpSwitchAuthenticationMIBGroups 22 }

    hpSwitchUserConfigGroup2 OBJECT-GROUP
        OBJECTS   { hpicfSwitchUserName,
                    hpicfSwitchOperatorName,
                    hpicfSwitchPortAccessName,
                    hpicfSwitchUserPassword,
                    hpicfSwitchOperatorPassword,
                    hpicfSwitchPortAccessPassword,
                    hpicfSwitchUserPasswordEncrypted,
                    hpicfSwitchOperatorPasswordEncrypted,
                    hpicfSwitchPortAccessPasswordEncrypted,
                    hpicfSwitchUserPasswordHashType,
                    hpicfSwitchOperatorPasswordHashType,
                    hpicfSwitchPortAccessPasswordHashType,
                    hpicfSwitchUserConfigStatus,
                    hpicfSwitchUserPwdAgingInterval,
                    hpicfSwitchOperatorPwdAgingInterval,
                    hpicfSwitchUserPwdLengthValue,
                    hpicfSwitchOperatorPwdLengthValue
                  }
        STATUS    deprecated
        DESCRIPTION "A collection of objects for configuring user-name/password
                     for operator/manager/port-access."
       ::= { hpSwitchAuthenticationMIBGroups 33 }

    hpSwitchUserConfigGroup3 OBJECT-GROUP
        OBJECTS   { hpicfSwitchUserName,
                    hpicfSwitchOperatorName,
                    hpicfSwitchPortAccessName,
                    hpicfSwitchUserPassword,
                    hpicfSwitchOperatorPassword,
                    hpicfSwitchPortAccessPassword,
                    hpicfSwitchUserPasswordEncrypted,
                    hpicfSwitchOperatorPasswordEncrypted,
                    hpicfSwitchPortAccessPasswordEncrypted,
                    hpicfSwitchUserPasswordHashType,
                    hpicfSwitchOperatorPasswordHashType,
                    hpicfSwitchPortAccessPasswordHashType,
                    hpicfSwitchUserConfigStatus,
                    hpicfSwitchUserPwdAgingInterval,
                    hpicfSwitchOperatorPwdAgingInterval,
                    hpicfSwitchUserPwdLengthValue,
                    hpicfSwitchOperatorPwdLengthValue,
                    hpicfSwitchNonPlaintextSha256,
                    hpicfSwitchUserPasswordHashSha256,
                    hpicfSwitchOperatorPasswordHashSha256
                  }
        STATUS    current
        DESCRIPTION "A collection of objects for configuring username and password
                     for operator, manager or port-access."
       ::= { hpSwitchAuthenticationMIBGroups 38 }

    hpSwitchAuthLocalMgmtPrivUserGroup1 OBJECT-GROUP
        OBJECTS   { hpSwitchLocalMgmtPrivUsernameStatus 
                  }
        STATUS      current
        DESCRIPTION "Row Status of objects for configuring
                     Local Management Privilege Groups"
       ::= { hpSwitchAuthenticationMIBGroups 23 }

    hpSwitchCertStatusGroup3  OBJECT-GROUP
        OBJECTS   {
                   hpSwitchServerNewCertKeySizeExists
                  }
        STATUS    current
        DESCRIPTION "A collection of objects for configuring 
                     Certificate Keys."
        ::= { hpSwitchAuthenticationMIBGroups 24 }

    hpSwitchAuthenticationConfigGroup2 OBJECT-GROUP
        OBJECTS     { hpSwitchNumLoginAttempts,
                      hpSwitchAuthLockoutDelay,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod
                    }
        STATUS      deprecated
        DESCRIPTION "A collection of objects for configuring the
                    authentication features."
        ::= { hpSwitchAuthenticationMIBGroups 25 }

   hpSwitchRadiusConfigGroup2 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus
                    }
        STATUS      deprecated
        DESCRIPTION "A collection of objects for configuring the
                    state of the RADIUS protocol."
        ::= { hpSwitchAuthenticationMIBGroups 26 }

    hpSwitchAuthenticationConfigGroup3 OBJECT-GROUP
        OBJECTS     { hpSwitchNumLoginAttempts,
                      hpSwitchAuthLockoutDelay,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod,
                      hpSwitchMinimumPasswordLength,
                      hpSwitchAuthAllowVlanTagged
                    }
        STATUS      deprecated
        DESCRIPTION "A collection of objects for configuring the
                    authentication features."
        ::= { hpSwitchAuthenticationMIBGroups 27 }
    
    hpSwitchAuthenticationConfigGroup4  OBJECT-GROUP
        OBJECTS   {
                   hpicfSwitchBypassUsername
                  }
        STATUS    current
        DESCRIPTION "A collection of objects which controls bypassing of the 
                     username during authentication to get Operator or Manager
                     access."
        ::= { hpSwitchAuthenticationMIBGroups 28 }
   
    hpSwitchRadiusConfigGroup3 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus,
                      hpSwitchRadiusTracking,
                      hpSwitchRadiusTrackingUserName
                      }
        STATUS      deprecated
        DESCRIPTION "A collection of objects for configuring the
                    state of the RADIUS protocol."
        ::= { hpSwitchAuthenticationMIBGroups 29 }

        hpSwitchRipAuthGroup OBJECT-GROUP
        OBJECTS     { hpSwitchRipIfAuthChain
                    }
        STATUS      deprecated
        DESCRIPTION "A collection of objects for configuring
                     RIP authentication."
        ::= { hpSwitchAuthenticationMIBGroups 31 }

    hpSwitchAuthenticationPasswordConfigGroup OBJECT-GROUP
        OBJECTS     { hpSwitchAuthPwdControlCheck,
                      hpSwitchAuthPwdUserNameCheck,
                      hpSwitchAuthPwdRepeatCharactersCheck,
                      hpSwitchAuthPwdRepeatPasswordCheck,
                      hpSwitchAuthPwdAgingCheck,
                      hpSwitchAuthPwdLogonDetailsCheck,
                      hpSwitchAuthPwdAgingValue,
                      hpSwitchAuthPwdHistoryCheck,
                      hpSwitchAuthPwdHistoryRecordsRange,
                      hpSwitchAuthPwdAlertBeforeExpiry,
                      hpSwitchAuthPwdExpiredUserLoginDays,
                      hpSwitchAuthPwdExpiredUserLoginAttempts,
                      hpSwitchAuthPwdUpdateInterval,
                      hpSwitchAuthenCompositionValue
                    }
        STATUS      current
        DESCRIPTION "A collection of objects for configuring the
                     password authentication features as per UCR
                     guidelines."
        ::= { hpSwitchAuthenticationMIBGroups 32 }

    hpSwitchAuthNotificationGroup    NOTIFICATION-GROUP
        NOTIFICATIONS {
	               hpSwitchPasswordExpiryNotify
	              }
        STATUS   current
        DESCRIPTION "A collection of objects that lists the authentication 
                      notifications."
        ::= { hpSwitchAuthenticationMIBGroups 35 } 
   
    hpSwitchRadiusConfigGroup4 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus,
                      hpSwitchRadiusServerDynAutzTimeWindowType                     
                      }
        STATUS      deprecated
        DESCRIPTION "A collection of objects for configuring the
                    state of the RADIUS protocol."
        ::= { hpSwitchAuthenticationMIBGroups 36 }

    hpSwitchAuthenticationConfigGroup5 OBJECT-GROUP
        OBJECTS     { hpSwitchNumLoginAttempts,
                      hpSwitchAuthLockoutDelay,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod,
                      hpSwitchMinimumPasswordLength,
                      hpSwitchAuthAllowVlanTagged,
                      hpSwitchAuthenLoginTwoFactorType,
                      hpSwitchAuthenEnableTwoFactorType,
                      hpSwitchAuthenLoginSecondAuthMethod,
                      hpSwitchAuthenEnableSecondAuthMethod,
                      hpSwitchAuthenClientPrimary,
                      hpSwitchAuthenClientSecondary
                    }
        STATUS      deprecated
        DESCRIPTION "A collection of objects for configuring the
                    authentication features."
        ::= { hpSwitchAuthenticationMIBGroups 37 }

    hpSwitchAuthLocalMgmtPrivUserGroup3 OBJECT-GROUP
        OBJECTS   {
            hpSwitchLocalMgmtPrivUsernameStr,
            hpSwitchLocalMgmtPrivUsernamePasswdType,
            hpSwitchLocalMgmtPrivUsernamePasswd,
            hpSwitchLocalMgmtPrivUsernameGrpIndex,
            hpSwitchLocalMgmtPwdUserAgingInterval,
            hpSwitchLocalMgmtPwdUserPasswdLengthValue,
            hpSwitchLocalMgmtPrivUsernamePasswdSha256
        }
        STATUS    current
        DESCRIPTION "A collection of objects for configuring
                     Local Management Privilege Groups"
       ::= { hpSwitchAuthenticationMIBGroups 39 }
    
   hpSwitchOspfAuthGroup1 OBJECT-GROUP
        OBJECTS     { hpSwitchOspfVirtIfAuthChain,
                      hpSwitchOspfIfAuthChain,
                      hpSwitchOspfVirtIfAuthKeyEncrypted,
                      hpSwitchOspfIfAuthKeyEncrypted
                    }
        STATUS      current
        DESCRIPTION "A collection of objects for configuring
                     OSPF authentication."
        ::= { hpSwitchAuthenticationMIBGroups 40 }

    hpSwitchRipAuthGroup1 OBJECT-GROUP
        OBJECTS     { hpSwitchRipIfAuthChain,
                      hpSwitchRip2IfConfAuthKeyEncrypted
                    }
        STATUS      current
        DESCRIPTION "A collection of objects for configuring
                     RIP authentication."
        ::= { hpSwitchAuthenticationMIBGroups 41 }

    hpSwitchAuthenticationConfigGroup6 OBJECT-GROUP
        OBJECTS     { hpSwitchNumLoginAttempts,
                      hpSwitchAuthLockoutDelay,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod,
                      hpSwitchMinimumPasswordLength,
                      hpSwitchAuthAllowVlanTagged,
                      hpSwitchAuthenLoginTwoFactorType,
                      hpSwitchAuthenEnableTwoFactorType,
                      hpSwitchAuthenLoginSecondAuthMethod,
                      hpSwitchAuthenEnableSecondAuthMethod,
                      hpSwitchAuthenClientPrimary,
                      hpSwitchAuthenClientSecondary,
                      hpSwitchAuthenHideSensitiveData
                    }
        STATUS      deprecated
        DESCRIPTION "A collection of objects for configuring the
                    authentication features."
        ::= { hpSwitchAuthenticationMIBGroups 42 }
    
    hpSwitchAuthenticationConfigGroup7 OBJECT-GROUP
        OBJECTS     { hpSwitchNumLoginAttempts,
                      hpSwitchAuthLockoutDelay,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod,
                      hpSwitchMinimumPasswordLength,
                      hpSwitchAuthAllowVlanTagged,
                      hpSwitchAuthenLoginTwoFactorType,
                      hpSwitchAuthenEnableTwoFactorType,
                      hpSwitchAuthenLoginSecondAuthMethod,
                      hpSwitchAuthenEnableSecondAuthMethod,
                      hpSwitchAuthenClientPrimary,
                      hpSwitchAuthenClientSecondary,
                      hpSwitchAuthenHideSensitiveData,
                      hpSwitchAuthUnlockUser,
                      hpSwitchAuthUserBasedLockout
                    }
        STATUS      deprecated
        DESCRIPTION "A collection of objects for configuring the
                     authentication features."
        ::= { hpSwitchAuthenticationMIBGroups 43 }

   hpSwitchRadiusConfigGroup5 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus,
                      hpSwitchRadiusServerDynAutzTimeWindowType,
                      hpSwitchRadiusCppmIdentity,
                      hpSwitchRadiusCppmKey,
                      hpSwitchRadiusCppmEncryptedKey
                      }
        STATUS      deprecated
        DESCRIPTION "A collection of objects for configuring the
                    state of the RADIUS protocol."
        ::= { hpSwitchAuthenticationMIBGroups 44 }

    hpSwitchFrontPanelSecurityGroup OBJECT-GROUP
        OBJECTS   {
            hpSwitchFpsPasswordClear,
            hpSwitchFpsFactoryReset,
            hpSwitchFpsPasswordRecovery,
            hpSwitchFpsDiagnosticResetClearButton,
            hpSwitchFpsDiagnosticResetSerialConsole,
            hpSwitchFpsDisplayInConfig
        }
        STATUS    current
        DESCRIPTION "A collection of objects for configuring front
                     panel security commands."
       ::= { hpSwitchAuthenticationMIBGroups 45 }
     
   hpSwitchRadiusConfigGroup6 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus,
                      hpSwitchRadiusServerDynAutzTimeWindowType,
                      hpSwitchRadiusCppmIdentity,
                      hpSwitchRadiusCppmKey,
                      hpSwitchRadiusCppmEncryptedKey,
                      hpSwitchRadiusDeadTimeInfinite,
                      hpSwitchRadiusTrackingInterval
                      }
              
        STATUS      deprecated
        DESCRIPTION "A collection of objects for configuring the
                    state of the RADIUS protocol."
        ::= { hpSwitchAuthenticationMIBGroups 46 }

    hpSwitchAuthenticationConfigGroup8 OBJECT-GROUP
        OBJECTS     { hpSwitchNumLoginAttempts,
                      hpSwitchAuthLockoutDelay,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod,
                      hpSwitchMinimumPasswordLength,
                      hpSwitchAuthAllowVlanTagged,
                      hpSwitchAuthenLoginTwoFactorType,
                      hpSwitchAuthenEnableTwoFactorType,
                      hpSwitchAuthenLoginSecondAuthMethod,
                      hpSwitchAuthenEnableSecondAuthMethod,
                      hpSwitchAuthenClientPrimary,
                      hpSwitchAuthenClientSecondary,
                      hpSwitchAuthenHideSensitiveData,
                      hpSwitchAuthUnlockUser,
                      hpSwitchAuthUserBasedLockout,
                      hpSwitchAuthenCachedReauthAuthorized
                    }
        STATUS      deprecated
        DESCRIPTION "A collection of objects for configuring the
                    authentication features."
        ::= { hpSwitchAuthenticationMIBGroups 47 }

   hpSwitchRadiusConfigGroup7 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus,
                      hpSwitchRadiusServerDynAutzTimeWindowType,
                      hpSwitchRadiusCppmIdentity,
                      hpSwitchRadiusCppmKey,
                      hpSwitchRadiusCppmEncryptedKey,
                      hpSwitchRadiusDeadTimeInfinite,
                      hpSwitchRadiusTrackingInterval,
                      hpSwitchRadiusTrackingPassword,
                      hpSwitchRadiusTrackDeadOnly,
                      hpSwitchRadiusTrackReqPktCount,
                      hpSwitchRadiusTrackPassEncrypt
                    }
        STATUS      deprecated
        DESCRIPTION "A collection of objects for configuring the
                    state of the RADIUS protocol."
        ::= { hpSwitchAuthenticationMIBGroups 48 }

    hpSwitchAuthenticationConfigGroup9 OBJECT-GROUP
        OBJECTS     { hpSwitchNumLoginAttempts,
                      hpSwitchAuthLockoutDelay,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod,
                      hpSwitchMinimumPasswordLength,
                      hpSwitchAuthAllowVlanTagged,
                      hpSwitchAuthenLoginTwoFactorType,
                      hpSwitchAuthenEnableTwoFactorType,
                      hpSwitchAuthenLoginSecondAuthMethod,
                      hpSwitchAuthenEnableSecondAuthMethod,
                      hpSwitchAuthenClientPrimary,
                      hpSwitchAuthenClientSecondary,
                      hpSwitchAuthenHideSensitiveData,
                      hpSwitchAuthUnlockUser,
                      hpSwitchAuthUserBasedLockout,
                      hpSwitchAuthenCachedReauthAuthorized,
                      hpSwitchAuthConsoleLockout
                    }
        STATUS      current
        DESCRIPTION "A collection of objects for configuring the
                    authentication features."
        ::= { hpSwitchAuthenticationMIBGroups 49 }

    hpSwitchTacacsConfigGroup2 OBJECT-GROUP
        OBJECTS     { hpSwitchTacacsTimeout,
                      hpSwitchTacacsAuthKey,
                      hpSwitchTacacsAuthKeyEncrypted,
                      hpSwitchTacacsServerIpAddr,
                      hpSwitchTacacsServerAddressType,
                      hpSwitchTacacsServerAddress,
                      hpSwitchTacacsServerKey,
                      hpSwitchTacacsServerKeyEncrypted,
                      hpSwitchTacacsServerStatus,
                      hpSwitchTacacsDeadTime
                    }
        STATUS      deprecated
        DESCRIPTION "A collection of objects for configuring the
                    state of the TACACS+ protocol."
        ::= { hpSwitchAuthenticationMIBGroups 50 }

    hpSwitchTacacsStatsGroup1 OBJECT-GROUP
        OBJECTS     { hpTacacsStatsTacacsServerIpAddr,
                      hpTacacsStatsTacacsServerAdrType,
                      hpTacacsStatsTacacsServerAddr,
                      hpTacacsStatsNumSessOpened,
                      hpTacacsStatsNumSessClosed,
                      hpTacacsStatsNumSessAborted,
                      hpTacacsStatsNumSessErrors,
                      hpTacacsStatsNumPktsIn,
                      hpTacacsStatsNumPktsOut,
                      hpTacacsStatsNumAuthPktsIn,
                      hpTacacsStatsNumAuthPktsOut,
                      hpTacacsStatsNumAuthPktsTimedOut,
                      hpTacacsStatsNumAutzPktsIn,
                      hpTacacsStatsNumAutzPktsOut,
                      hpTacacsStatsNumAutzPktsTimedOut,
                      hpTacacsStatsNumAcctPktsIn,
                      hpTacacsStatsNumAcctPktsOut,
                      hpTacacsStatsNumAcctPktsTimedOut
                    }
        STATUS      current
        DESCRIPTION "A collection of objects for viewing the
                    status information of the TACACS+ protocol."
        ::= { hpSwitchAuthenticationMIBGroups 51 }

    hpSwitchTacacsOobmGroup1 OBJECT-GROUP
        OBJECTS     { hpSwitchTacacsServerIpAddr,
                      hpSwitchTacacsServerAddressType,
                      hpSwitchTacacsServerAddress,
                      hpSwitchTacacsServerIsOobm
                    }
        STATUS      current
        DESCRIPTION "A collection of objects for configuring the
                    TACACS+ server entry with support for OOBM
                    (Out of Band Management) interface."
        ::= { hpSwitchAuthenticationMIBGroups 52 }

   hpSwitchRadiusConfigGroup8 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus,
                      hpSwitchRadiusServerDynAutzTimeWindowType,
                      hpSwitchRadiusCppmIdentity,
                      hpSwitchRadiusCppmKey,
                      hpSwitchRadiusCppmEncryptedKey,
                      hpSwitchRadiusDeadTimeInfinite,
                      hpSwitchRadiusTrackingInterval,
                      hpSwitchRadiusTrackingPassword,
                      hpSwitchRadiusTrackDeadOnly,
                      hpSwitchRadiusTrackReqPktCount,
                      hpSwitchRadiusTrackPassEncrypt,
                      hpSwitchRadiusFramedIpv4Address
                    }
        STATUS      deprecated
        DESCRIPTION "A collection of objects for configuring the
                    state of the RADIUS protocol."
        ::= { hpSwitchAuthenticationMIBGroups 53 }

   hpSwitchRadiusConfigGroup9 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus,
                      hpSwitchRadiusServerDynAutzTimeWindowType,
                      hpSwitchRadiusCppmIdentity,
                      hpSwitchRadiusCppmKey,
                      hpSwitchRadiusCppmEncryptedKey,
                      hpSwitchRadiusDeadTimeInfinite,
                      hpSwitchRadiusTrackingInterval,
                      hpSwitchRadiusTrackingPassword,
                      hpSwitchRadiusTrackDeadOnly,
                      hpSwitchRadiusTrackReqPktCount,
                      hpSwitchRadiusTrackPassEncrypt,
                      hpSwitchRadiusServerFqdn,
                      hpSwitchRadiusServerIsClearPass
                    }
        STATUS      deprecated
        DESCRIPTION "A collection of objects for configuring the
                    state of the RADIUS protocol."
        ::= { hpSwitchAuthenticationMIBGroups 54 }

   hpSwitchRadiusConfigGroup10 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus,
                      hpSwitchRadiusServerDynAutzTimeWindowType,
                      hpSwitchRadiusCppmIdentity,
                      hpSwitchRadiusCppmKey,
                      hpSwitchRadiusCppmEncryptedKey,
                      hpSwitchRadiusDeadTimeInfinite,
                      hpSwitchRadiusTrackingInterval,
                      hpSwitchRadiusTrackingPassword,
                      hpSwitchRadiusTrackDeadOnly,
                      hpSwitchRadiusTrackReqPktCount,
                      hpSwitchRadiusTrackPassEncrypt,
                      hpSwitchRadiusFramedIpv4Address,
                      hpSwitchRadiusServerFqdn,
                      hpSwitchRadiusServerIsClearPass,
                      hpSwitchRadiusFqdnRetry
                    }
        STATUS      deprecated
        DESCRIPTION "A collection of objects for configuring the
                    state of the RADIUS protocol."
        ::= { hpSwitchAuthenticationMIBGroups 55 }

   hpSwitchRadiusConfigGroup11 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus,
                      hpSwitchRadiusServerDynAutzTimeWindowType,
                      hpSwitchRadiusCppmIdentity,
                      hpSwitchRadiusCppmKey,
                      hpSwitchRadiusCppmEncryptedKey,
                      hpSwitchRadiusDeadTimeInfinite,
                      hpSwitchRadiusTrackingInterval,
                      hpSwitchRadiusTrackingPassword,
                      hpSwitchRadiusTrackDeadOnly,
                      hpSwitchRadiusTrackReqPktCount,
                      hpSwitchRadiusTrackPassEncrypt,
                      hpSwitchRadiusFramedIpv4Address,
                      hpSwitchRadiusServerFqdn,
                      hpSwitchRadiusServerIsClearPass,
                      hpSwitchRadiusFqdnRetry
                    }
        STATUS      deprecated
        DESCRIPTION "A collection of objects for configuring the
                    state of the RADIUS protocol."
        ::= { hpSwitchAuthenticationMIBGroups 56 }
        
    hpSwitchTacacsConfigGroup3 OBJECT-GROUP
        OBJECTS     { hpSwitchTacacsTimeout,
                      hpSwitchTacacsAuthKey,
                      hpSwitchTacacsAuthKeyEncrypted,
                      hpSwitchTacacsServerIpAddr,
                      hpSwitchTacacsServerAddressType,
                      hpSwitchTacacsServerAddress,
                      hpSwitchTacacsServerKey,
                      hpSwitchTacacsServerKeyEncrypted,
                      hpSwitchTacacsServerStatus,
                      hpSwitchTacacsDeadTime,
                      hpSwitchTacacsOrderingSequence
                    }
        STATUS      current
        DESCRIPTION "A collection of objects for configuring the
                    state of the TACACS+ protocol."
        ::= { hpSwitchAuthenticationMIBGroups 59 }    

   hpSwitchRadiusConfigGroup12 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus,
                      hpSwitchRadiusServerDynAutzTimeWindowType,
                      hpSwitchRadiusCppmIdentity,
                      hpSwitchRadiusCppmKey,
                      hpSwitchRadiusCppmEncryptedKey,
                      hpSwitchRadiusDeadTimeInfinite,
                      hpSwitchRadiusTrackingInterval,
                      hpSwitchRadiusTrackingPassword,
                      hpSwitchRadiusTrackDeadOnly,
                      hpSwitchRadiusTrackReqPktCount,
                      hpSwitchRadiusTrackPassEncrypt,
                      hpSwitchRadiusFramedIpv4Address,
                      hpSwitchRadiusServerFqdn,
                      hpSwitchRadiusServerIsClearPass,
                      hpSwitchRadiusFqdnRetry,
                      hpSwitchRadiusTLSTimeout,
                      hpSwitchRadiusTLSConnectionTimeout,
                      hpSwitchRadiusTLSDeadTime,
                      hpSwitchRadiusTLSDeadTimeInfinite,
                      hpSwitchRadiusTLSEnable,
                      hpSwitchRadiusTLSPort,
                      hpSwitchRadiusTLSRetryTimer
                    }
        STATUS      current
        DESCRIPTION "A collection of objects for configuring the
                    state of the RADIUS protocol."
        ::= { hpSwitchAuthenticationMIBGroups 60 }

    hpSwitchAAAServerGroup2   OBJECT-GROUP
        OBJECTS   { hpSwitchAAAServerGroupName,
                    hpSwitchAAAServerGroupServerInetType,
                    hpSwitchAAAServerGroupServerInetAddr,
                    hpSwitchAAAServerGroupStatus,
                    hpSwitchAAAServerGroupServerFqdn,
                    hpSwitchAAAServerGroupTLSEnable
                  }
        STATUS    current
        DESCRIPTION "A collection of objects for configuring RADIUS server groups."
       ::= { hpSwitchAuthenticationMIBGroups 61 }
END
