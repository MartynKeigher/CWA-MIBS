--------------------------------------------------------------------
-- SNMPv2-SMI.my:  SNMPv2 Structure of Management Information
--
-- May 1994, Jeffrey T. Johnson
--
-- Copyright (c) 1994-1996 by cisco Systems, Inc.
-- All rights reserved.
-- 
--------------------------------------------------------------------
-- Revision 3.3  1996/08/14 10:58:57  mordock
-- CSCdi65979:  mibs dont load cleanly into HP Openview
-- cosmetic change to get mibs to load cleanly into HP Openview.
-- also added InterfaceIndexOrZero textual-convention to CISCO-TC
--
-- Revision 3.2  1995/11/17  08:37:13  hampton
-- Remove old entries from the RCS header logs.
--
-- Revision 3.1  1995/11/09  10:52:27  shaker
-- Bump version numbers from 2.x to 3.x.
--
-- Revision 2.1  1995/06/07  20:03:18  hampton
-- Bump version numbers from 1.x to 2.x.
--
--------------------------------------------------------------------
--
--      The following is extracted from RFC 1442
--      All macro definitions have been commented out because they are
--      predefined in the mib compiler

          SNMPv2-SMI DEFINITIONS ::= BEGIN


          -- the path to the root

          org            OBJECT IDENTIFIER ::= { iso 3 }
          dod            OBJECT IDENTIFIER ::= { org 6 }
          internet       OBJECT IDENTIFIER ::= { dod 1 }

          directory      OBJECT IDENTIFIER ::= { internet 1 }

          mgmt           OBJECT IDENTIFIER ::= { internet 2 }

          experimental   OBJECT IDENTIFIER ::= { internet 3 }

          private        OBJECT IDENTIFIER ::= { internet 4 }
          enterprises    OBJECT IDENTIFIER ::= { private 1 }

          security       OBJECT IDENTIFIER ::= { internet 5 }

          snmpV2         OBJECT IDENTIFIER ::= { internet 6 }

          -- transport domains
          snmpDomains    OBJECT IDENTIFIER ::= { snmpV2 1 }

          -- transport proxies
          snmpProxys     OBJECT IDENTIFIER ::= { snmpV2 2 }

          -- module identities
          snmpModules    OBJECT IDENTIFIER ::= { snmpV2 3 }

		  mib-2	OBJECT IDENTIFIER  ::=  {  mgmt  1  }

          -- definitions for information modules

--          MODULE-IDENTITY MACRO ::=
--          BEGIN
--              TYPE NOTATION ::=
--                            "LAST-UPDATED" value(Update UTCTime)
--                            "ORGANIZATION" Text
--                            "CONTACT-INFO" Text
--                            "DESCRIPTION" Text
--                            RevisionPart
--
--              VALUE NOTATION ::=
--                            value(VALUE OBJECT IDENTIFIER)
--
--              RevisionPart ::=
--                            Revisions
--                          | empty
--              Revisions ::=
--                            Revision
--                          | Revisions Revision
--              Revision ::=
--                            "REVISION" value(Update UTCTime)
--                            "DESCRIPTION" Text
--
              -- uses the NVT ASCII character set
--              Text ::= """" string """"
--          END


--          OBJECT-IDENTITY MACRO ::=
--          BEGIN
--              TYPE NOTATION ::=
--                            "STATUS" Status
--                            "DESCRIPTION" Text
--                            ReferPart
--
--              VALUE NOTATION ::=
--                            value(VALUE OBJECT IDENTIFIER)
--
--              Status ::=
--                            "current"
--                          | "obsolete"
--
--              ReferPart ::=
--                          "REFERENCE" Text
--                        | empty
--
--              Text ::= """" string """"
--          END

          -- names of objects

--          ObjectName ::=
--              OBJECT IDENTIFIER


          -- syntax of objects

--          ObjectSyntax ::=
--             CHOICE {
--                  simple
--                      SimpleSyntax,

                    -- note that SEQUENCEs for conceptual tables and
                    -- rows are not mentioned here...

--                 application-wide
--                    ApplicationSyntax
--           }


          -- built-in ASN.1 types

--          SimpleSyntax ::=
--              CHOICE {
                  -- INTEGERs with a more restrictive range
                  -- may also be used
--                  integer-value
--                      INTEGER (-2147483648..2147483647),
--
--                  string-value
--                      OCTET STRING,
--
--                  objectID-value
--                      OBJECT IDENTIFIER,
--
                  -- only the enumerated form is allowed
--                  bit-value
--                      BIT STRING
--              }



          -- indistinguishable from INTEGER, but never needs more than
          -- 32-bits for a two's complement representation
--          Integer32 ::=
--              [UNIVERSAL 2]
--                  IMPLICIT INTEGER (-2147483648..2147483647)


          -- application-wide types

--          ApplicationSyntax ::=
--              CHOICE {
--                  ipAddress-value
--                      IpAddress,
--
--                  counter-value
--                      Counter32,
--
--                  gauge-value
--                      Gauge32,
--
--                  timeticks-value
--                      TimeTicks,
--
--                  arbitrary-value
--                      Opaque,
--
--                  nsapAddress-value
--                      NsapAddress,
--
--                  big-counter-value
--                      Counter64,
--
--                  unsigned-integer-value
--                      UInteger32
--              }

          -- in network-byte order
          -- (this is a tagged type for historical reasons)
--          IpAddress ::=
--              [APPLICATION 0]
--                  IMPLICIT OCTET STRING (SIZE (4))

          -- this wraps
--          Counter32 ::=
--              [APPLICATION 1]
--                  IMPLICIT INTEGER (0..4294967295)

          -- this doesn't wrap
--          Gauge32 ::=
--              [APPLICATION 2]
--                  IMPLICIT INTEGER (0..4294967295)

          -- hundredths of seconds since an epoch
--          TimeTicks ::=
--              [APPLICATION 3]
--                  IMPLICIT INTEGER (0..4294967295)

          -- for backward-compatibility only
--          Opaque ::=
--              [APPLICATION 4]
--                  IMPLICIT OCTET STRING

          -- for OSI NSAP addresses
          -- (this is a tagged type for historical reasons)
--          NsapAddress ::=
--              [APPLICATION 5]
--                  IMPLICIT OCTET STRING (SIZE (1 | 4..21))

          -- for counters that wrap in less than one hour with only 32 bits
--          Counter64 ::=
--              [APPLICATION 6]
--                  IMPLICIT INTEGER (0..18446744073709551615)

          -- an unsigned 32-bit quantity
--          UInteger32 ::=
--              [APPLICATION 7]
--                  IMPLICIT INTEGER (0..4294967295)


          -- definition for objects

--          OBJECT-TYPE MACRO ::=
--          BEGIN
--              TYPE NOTATION ::=
--                            "SYNTAX" type(Syntax)
--                            UnitsPart
--                            "MAX-ACCESS" Access
--                            "STATUS" Status
--                            "DESCRIPTION" Text
--                            ReferPart
--                            IndexPart
--                            DefValPart
--
--              VALUE NOTATION ::=
--                            value(VALUE ObjectName)
--
--              UnitsPart ::=
--                            "UNITS" Text
--                          | empty
--
--              Access ::=
--                            "not-accessible"
--                          | "read-only"
--                          | "read-write"
--                          | "read-create"
--
--              Status ::=
--                            "current"
--                          | "deprecated"
--                          | "obsolete"
--
--              ReferPart ::=
--                            "REFERENCE" Text
--                          | empty
--
--              IndexPart ::=
--                            "INDEX"    "{" IndexTypes "}"
--                          | "AUGMENTS" "{" Entry      "}"
--                          | empty
--              IndexTypes ::=
--                            IndexType
--                          | IndexTypes "," IndexType
--              IndexType ::=
--                            "IMPLIED" Index
--                          | Index
--              Index ::=
                              -- use the SYNTAX value of the
                              -- correspondent OBJECT-TYPE invocation
--                            value(Indexobject ObjectName)
--              Entry ::=
                              -- use the INDEX value of the
                              -- correspondent OBJECT-TYPE invocation
--                            value(Entryobject ObjectName)
--
--              DefValPart ::=
--                            "DEFVAL" "{" value(Defval Syntax) "}"
--                          | empty
--
              -- uses the NVT ASCII character set
--              Text ::= """" string """"
--          END


          -- definitions for notifications

--          NOTIFICATION-TYPE MACRO ::=
--          BEGIN
--              TYPE NOTATION ::=
--                            ObjectsPart
--                            "STATUS" Status
--                            "DESCRIPTION" Text
--                            ReferPart
--
--              VALUE NOTATION ::=
--                            value(VALUE OBJECT IDENTIFIER)
--
--              ObjectsPart ::=
--                            "OBJECTS" "{" Objects "}"
--                          | empty
--              Objects ::=
--                            Object
--                          | Objects "," Object
--              Object ::=
--                            value(Name ObjectName)
--
--              Status ::=
--                            "current"
--                          | "deprecated"
--                          | "obsolete"
--
--              ReferPart ::=
--                          "REFERENCE" Text
--                        | empty
--
              -- uses the NVT ASCII character set
--              Text ::= """" string """"
--          END


          END
