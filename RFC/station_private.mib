VERTICAL-STATION-MIB DEFINITIONS ::= BEGIN

IMPORTS
             Gauge, enterprises
                     FROM RFC1155-SMI
             DisplayString
                     FROM RFC1213-MIB
             OBJECT-TYPE
                     FROM RFC-1212
             TRAP-TYPE
                     FROM RFC-1215;
             

vertical OBJECT IDENTIFIER ::= { enterprises 2338 }  


     --  This MIB module uses the extended OBJECT-TYPE macro as
     --  defined in RFC 1212.
  
     --  This is the MIB module for Vertical Networks' Station Card
     --  and contain definitions of managed objects for configuration,
     --  control and status of the InstantOffice station modules.
     --  This MIB is found in the private.enterprise branch of the
     --  MIB tree.

     --  Author  : Raju Viswambharan
     --  Version : 1.0
     --  Date    : 16 Feb, 1998
     --  Comments : created
 

     -- This MIB is structured into four groups:
	
     --	  The Common Group:       Which contains status and configuration
	 --                           information that are common to all Station
	 --	                          devices within the system

	 --   The Station Card Group: Contains status, control and configuraion
	 --                           information about all cards containing station
	 --							  devices  within the system.This information is 
     -- 						  arranged into three tables, the Card Table, 
	 --							  the DeviceTable and the ChannelTable to define
	 --							  card, device and channel specific information 
	 --							  respectfully

	 --   The Digit Table Group:  Contains configuration information of digits that
	 --                           can be dialled. Currently this group contains just
	 --							  one table, the FirstDigitTable which contain settings 
	 --							  for each digit (0 to 9) dialed as the first digit .

	 --   The External Voice 
	 --       Mail System Group:  This group contains configuration information used 
	 --                           to interface with an external voice mail system. 
	 --							  This group is subdivided into subgroups depending 
	 --							  on the type of the voice mail system used. Currently,
	 --							  there is just one subgroup: the ATT_System_25 subgroup.


	 -- 11 27 2000 madhu #10250;Changes:
	 -- vStationCardEntry            -> VStationCardEntry
	 -- CARD_TYPE_NOT_CONFIGURED     -> card_type_NOT_CONFIGURED
	 -- CARD_TYPE_24_CHANNEL_STATION -> card_type_24_CHANNEL_STATION
	 -- CARD_TYPE_BRIDGE1            -> card_type_BRIDGE1
	 -- Disabled                     -> disabled
	 -- Enabled                      -> enabled
	 -- Removed                      -> removed
	 -- vStationDeviceEntry          -> VStationDeviceEntry
	 -- DEVundef                     -> devUndef
	 -- DEVstation                   -> devStation 
	 -- vStationChannelEntry         -> VStationChannelEntry
	 -- PBX                          -> pbx
	 -- Enhanced_CallWaiting         -> enhanced_CallWaiting
	 -- CALL_STATE_VOID              -> call_state_VOID
	 -- CALL_STATE_IDLE              -> call_state_IDLE
	 -- CALL_STATE_DIALING           -> call_state_DIALING
	 -- CALL_STATE_COLLECT_FIRST_DIGIT -> call_state_COLLECT_FIRST_DIGIT 
	 -- CALL_STATE_COLLECT_DIGITS      -> call_state_COLLECT_DIGITS
	 -- CALL_STATE_CALL_OFFERED        -> call_state_CALL_OFFERED
	 -- CALL_STATE_PROCEEDING          -> call_state_PROCEEDING
	 -- CALL_STATE_RINGING             -> call_state_RINGING
	 -- CALL_STATE_ALERTING            -> call_state_ALERTING
	 -- CALL_STATE_CONNECTED           -> call_state_CONNECTED
	 -- CALL_STATE_DISCONNECTING       -> call_state_DISCONNECTING
	 -- CALL_STATE_FAILED              -> call_state_FAILED
	 -- CALL_STATE_UNAVAILABLE         -> call_state_UNAVAILABLE
	 -- CALL_STATE_OFFHOOK             -> call_state_OFFHOOK
	 -- CALL_STATE_INITIALIZE          -> call_state_INITIALIZE
	 -- CALL_STATE_INITIALIZING        -> call_state_INITIALIZING
	 -- CALL_STATE_DIAL_REQUEST        -> call_state_DIAL_REQUEST
	 -- CALL_STATE_HELD                -> call_state_HELD
	 -- CALL_STATE_FEATURE_INVOKED     -> call_state_FEATURE_INVOKED
	 -- CALL_STATE_OFFHOOK_IDLE        -> call_state_OFFHOOK_IDLE
	 -- CALL_STATE_OFFHOOK_ACTIVE      -> call_state_OFFHOOK_ACTIVE
	 -- CALL_STATE_OUT_OF_SERVICE      -> call_state_OUT_OF_SERVICE
	 -- CALL_STATE_OUTPULSING          -> call_state_OUTPULSING
	 -- vStationFirstDigitEntry        -> VStationFirstDigitEntry
	 -- FC_VOID                        -> fc_VOID
	 -- FC_HOLD_CALL                   -> fc_HOLD_CALL
	 -- FC_PARK_CALL                   -> fc_PARK_CALL
	 -- FC_STATION_CALL                -> fc_STATION_CALL
	 -- FC_LONG_DISTANCE_CALL          -> fc_LONG_DISTANCE_CALL
	 -- FC_INTERNATIONAL_CALL          -> fc_INTERNATIONAL_CALL
	 -- FC_LOCAL_CALL                  -> fc_LOCAL_CALL
	 -- FC_OPERATOR_CALL               -> fc_OPERATOR_CALL
	 -- FC_RECEPTIONIST_CALL           -> fc_RECEPTIONIST_CALL
	 -- FC_CAMP_ON_CALL                -> fc_CAMP_ON_CALL
	 -- vStationVMCallHandleEntry      -> VStationVMCallHandleEntry
	 -- VStationCannotPlayTone         -> vStationCannotPlayTone
	 -- VStationCannotCancelTone       -> vStationCannotCancelTone
	 -- VStationCannotAttachDigitCollector  -> vStationCannotAttachDigitCollector
	 -- VStationCannotReleaseDigitCollector -> vStationCannotReleaseDigitCollector
	 -- VStationRECONFIG_COMPLETE           -> vStationRECONFIG_COMPLETE
	 -- VStationRECONFIG_ERROR              -> vStationRECONFIG_ERROR
	 -- vStationDigitTimeout from   vStationFirstDigitEntry 5 removed; since no two node have same name(talk with Rick)
	 
	  --The following changed to read-only
      --1) vStationFirstDigitTimeout
      --2) vStationDigitTimeout
      --3) vStationOffHookTimeout
      --4) vStationExternalDialDigit
      --5) vStationNumStationCards
      --6) vStationDeviceEnabled
      --7) vStationChannelMWIType
      --8) vStationChannelOperationMode
      --9) vStationChannelState
      --10) vStationChannelType
	 vStationModule    OBJECT IDENTIFIER ::= {vertical 7}
								   
    
     -- The Common Group

     -- Implementation of this group is mandatory for all Vertical
     -- InstantOffice systems.
       vStationCommonGroup
       	OBJECT IDENTIFIER ::= { vStationModule 1 }


       vStationFirstDigitTimeout OBJECT-TYPE
             SYNTAX  INTEGER
             --ACCESS  read-write
             ACCESS  read-only
             STATUS  mandatory
             DESCRIPTION
                "Specifies the maximum number of seconds to wait for
				 the first digit."
            ::= { vStationCommonGroup 1 }

	   vStationDigitTimeout OBJECT-TYPE
             SYNTAX  INTEGER
             ACCESS  read-only
             STATUS  mandatory
             DESCRIPTION
                "Specifies the maximum number of seconds to wait
				 between digits."
            ::= { vStationCommonGroup 2 }

       vStationOffHookTimeout OBJECT-TYPE
             SYNTAX  INTEGER
             ACCESS  read-only
             STATUS  mandatory
             DESCRIPTION
                "Specifies the maximum number of seconds to wait for
				 the user to hang up phone after call disconnects or user
				 executes an invalid operation. Howler tone is applied at
				 timeout."
            ::= { vStationCommonGroup 3 }

       vStationNumStationCards OBJECT-TYPE
             SYNTAX  INTEGER
             ACCESS  read-only
             STATUS  mandatory
             DESCRIPTION
                "Specifies the number of station cards installed in 
				 the system."
            ::= { vStationCommonGroup 4 }

       vStationExternalDialDigit OBJECT-TYPE
             SYNTAX DisplayString (SIZE (0..1))
             ACCESS  read-only
             STATUS  mandatory
             DESCRIPTION
                "Identifies the starting digit for making an external
				 call."
            ::= { vStationCommonGroup 5 }


     
	 -- The StationCard Group

     -- Implementation of this group is mandatory for all Vertical
     -- InstantOffice systems.  
	 -- This group contains three tables: The Card table, the Device table 
	 -- and the Channel table.

     vStationCardGroup
       OBJECT IDENTIFIER ::= { vStationModule 2 }


     -- The Card Table 
		
       vStationCardTable OBJECT-TYPE
              SYNTAX  SEQUENCE OF VStationCardEntry
              ACCESS  not-accessible
              STATUS  mandatory
              DESCRIPTION
               "Table of status, control and configuraion about
                cards containing station devices within the system. 
				There are as many entries as there are cards containing
				station devices"
       ::= { vStationCardGroup 1 }

       vStationCardEntry OBJECT-TYPE
             SYNTAX  VStationCardEntry
             ACCESS  not-accessible
             STATUS  mandatory
             DESCRIPTION
              "An entry in the Vertical Station Card table."
             INDEX {vStationCardSlotNumber}
             ::= {vStationCardTable 1}
     
       VStationCardEntry ::=
            SEQUENCE {
              vStationCardSlotNumber
                 INTEGER,
			  vStationCardType
				 INTEGER,
			  vStationCardIOPortAddress     
                 INTEGER,
              vStationCardState
                 INTEGER,
			  vStationCardErrorLED
                 INTEGER,
              vStationCardReadyLED
                 INTEGER
            }


 	  vStationCardSlotNumber OBJECT-TYPE
              SYNTAX  INTEGER (1..14)
              ACCESS  read-only
              STATUS  mandatory
              DESCRIPTION
                 "Physical slot in the system in which the 
				  card is installed."

              ::= { vStationCardEntry 1}

	  vStationCardType OBJECT-TYPE
              SYNTAX  INTEGER {
						cardTYPE-NOT-CONFIGURED          (0),
						cardTYPE-24-CHANNEL-STATION      (2),
--						cardTYPE-8-CHANNEL-CO_POTS       (3),
						cardTYPE-RESOURCE-SWITCH-CARD	 (4),
						cardTYPE-8-CHANNEL-STATION       (23),
						cardTYPE-GECKO                   (24),
						cardTYPE-PYTHON                  (25),
						cardTYPE-8-CHANNEL-ANALOG-UNIVERSAL (29)
					  }    
              ACCESS  read-only
              STATUS  mandatory
              DESCRIPTION
                 "The Vertical's card Type. The following types are defined:
					cardTYPE-NOT-CONFIGURED          = 0,
					cardTYPE-24-CHANNEL-STATION      = 2,
					cardTYPE-RESOURCE-SWITCH-CARD    = 4,
					cardTYPE-8-CHANNEL-STATION	     = 23,
					cardTYPE-GECKO				     = 24,
					cardTYPE-PYTHON                  = 25,
					cardTYPE-8-CHANNEL-ANALOG-UNIVERSAL = 29"
              ::= { vStationCardEntry 2}

       vStationCardIOPortAddress OBJECT-TYPE
             SYNTAX  INTEGER (0..'7fffffff'h)
             ACCESS  read-only
             STATUS  mandatory
             DESCRIPTION
                "The ISA bus base address for this Card."

            ::= { vStationCardEntry  3}


		vStationCardState OBJECT-TYPE
              SYNTAX  INTEGER {
							disabled (0),
							enabled	 (1),
							removed	 (255)
			  }
              ACCESS  read-only
              STATUS  mandatory
              DESCRIPTION
                 "The current status of the card. The valid 
				  values are 0    -> Disabled,
							 1    -> Enabled,
							 0xff -> Removed."

              ::= { vStationCardEntry 4}

      vStationCardErrorLED OBJECT-TYPE
              SYNTAX  INTEGER (0..1)
              ACCESS  read-only
              STATUS  mandatory
              DESCRIPTION
                 "All Vertical cards have an ERROR LED and
                  a READY LED.  The combined values of these
                  LEDs are as follows -
                  ERRORLed    READYLed VALUE OPERATIONAL DEFINITION
                  OFF         OFF      (0 0) Invalid state  
                  ON          OFF      (1 0) Just after power up. This state 
                                             remains until card is 
                                              ready to service io.
                  ON          ON       (1 1) Statue during software initialization 
                  OFF         ON       (0 1) The normal operational state
                                              of the card."

              ::=  { vStationCardEntry 5}



       vStationCardReadyLED OBJECT-TYPE
              SYNTAX INTEGER (0..1)
              ACCESS  read-only
              STATUS  mandatory
              DESCRIPTION
                   "All Vertical cards have a READY LED and
                    an ERROR LED.  The combined values of these
                    LEDs are as follows -
                    ERRORLed    READYLed  OPERATIONAL DEFINITION
                    OFF         OFF       invalid state
                    ON          OFF       Just after power up. This 
                                          state remains until card is 
                                          ready to service io.
                    ON          ON        Statue during software initialization
                    OFF         ON        The normal operational state of the card."

              ::=  { vStationCardEntry 6}


	
     -- The Device Table 
		
       vStationDeviceTable OBJECT-TYPE
              SYNTAX  SEQUENCE OF VStationDeviceEntry
              ACCESS  not-accessible
              STATUS  mandatory
              DESCRIPTION
               "Table of status, control and configuraion about
                station devices within the system. There are as 
				many entries as there are station devices."
       ::= { vStationCardGroup 2 }

       vStationDeviceEntry OBJECT-TYPE
             SYNTAX  VStationDeviceEntry
             ACCESS  not-accessible
             STATUS  mandatory
             DESCRIPTION
              "An entry in the Vertical Station device Configuration
               table."
             INDEX {vStationDeviceSlotNumber}
             ::= {vStationDeviceTable 1}
     
       VStationDeviceEntry ::=
            SEQUENCE {
              vStationDeviceSlotNumber
                 INTEGER,
			  vStationDeviceDeviceNumber
				 INTEGER,
			  vStationDeviceIfIndex
				 INTEGER,
			  vStationDeviceBaseIOAddress
                 INTEGER,
			  vStationDeviceEnabled
                 INTEGER,
			  vStationDeviceInterrupt
                 INTEGER,
              vStationDeviceNumChannels      
                 INTEGER,
			  vStationDeviceMVIPStartingChannel
                 INTEGER,
              vStationDeviceMVIPStream
                 INTEGER,
			  vStationDeviceType
                 INTEGER
--TRACK 13415 dmf 07/12/02 remove:              vStationDeviceChangePending                
--                 INTEGER
            }


     vStationDeviceSlotNumber OBJECT-TYPE
              SYNTAX  INTEGER (0..255)
              ACCESS  read-only
              STATUS  mandatory
              DESCRIPTION
                 "Physical slot number inside the system in 
				  which the card containing this device is 
				  installed"
              ::= { vStationDeviceEntry 1}

	  vStationDeviceDeviceNumber OBJECT-TYPE
              SYNTAX  INTEGER (0..255)  
              ACCESS  read-only
              STATUS  mandatory
              DESCRIPTION
                 "The logical device number for this station 
				  device in its card."
              ::= { vStationDeviceEntry 2}

       vStationDeviceIfIndex OBJECT-TYPE
             SYNTAX  INTEGER (1..'7fffffff'h)
             ACCESS  read-only
             STATUS  mandatory
             DESCRIPTION
                "The interface Index for this device. The value for this object  
				  correlates to the IfIndex found in MIB-II."

            ::= { vStationDeviceEntry 3 }
	
	  vStationDeviceBaseIOAddress OBJECT-TYPE
             SYNTAX  INTEGER (0..'7fffffff'h)
             ACCESS  read-only
             STATUS  mandatory
             DESCRIPTION
                "The ISA bus base address for this Card."

            ::= { vStationDeviceEntry  4}

      vStationDeviceEnabled OBJECT-TYPE
             SYNTAX  INTEGER {
					 disabled (0),
                     enabled (1)
                     }
             ACCESS  read-only
             STATUS  mandatory
             DESCRIPTION
                "Setting this variable to Disabled will
                 disable this particular station device. "

            ::= { vStationDeviceEntry 5}

	  vStationDeviceInterrupt OBJECT-TYPE
             SYNTAX  INTEGER (1..2147483647)
             ACCESS  read-only
             STATUS  mandatory
             DESCRIPTION
                "Interrupt Request level for this card. "

            ::= { vStationDeviceEntry 6}

	  vStationDeviceNumChannels OBJECT-TYPE
             SYNTAX  INTEGER (1..'7fffffff'h)
             ACCESS  read-only
             STATUS  mandatory
             DESCRIPTION
                "The ISA bus address for this Card."

            ::= { vStationDeviceEntry  7}

      vStationDeviceMVIPStartingChannel OBJECT-TYPE
              SYNTAX  INTEGER (0..255)
              ACCESS  read-only
              STATUS  mandatory
              DESCRIPTION
                 "Vertical card revision level."

              ::= { vStationDeviceEntry 8}

	 vStationDeviceMVIPStream OBJECT-TYPE
              SYNTAX  INTEGER (0..255)
              ACCESS  read-only
              STATUS  mandatory
              DESCRIPTION
                 "Vertical card identification number."
              ::= { vStationDeviceEntry 9}

	 vStationDeviceType OBJECT-TYPE
              SYNTAX  INTEGER {
					devUndef (0),
--					DEVt1CAS (1),
--					DEVt1CCS (2),
--					DEVt1CCSnoD (3),
--					DEVe1CAS (4),
--					DEVe1CCS (5),
--					DEVe1CCSnoD (6),
--					DEVcoPots (7),
					devStation (8)
--					DEVDSPMgr (9),
--					DEVRicRes (10),
--					DEVRicRIB (11),
--					DEVSwitch (12),
--					DEVHDLCMgr (13),
--					DEV56KCSM (14),
--					DEVAudio (15)
				}
              ACCESS  read-only
              STATUS  mandatory
              DESCRIPTION
                 "Specifies the Type of this device
				  Valid values are :
					devUndef,			//  0 : undefined
					devStation,         //  8 : Station channels"
              ::= { vStationDeviceEntry 10}
       --madhu 11 16 2000 #5613; value range is changed from (1..'7fffffff'h) to (0..'7fffffff'h)
--TRACK 13415 dmf 07/12/02 remove:         vStationDeviceChangePending OBJECT-TYPE
--           SYNTAX  INTEGER (0..'7fffffff'h)
--madhu 11 07 2000 #6201
             --ACCESS  read-write
--             ACCESS  read-only
--           STATUS  mandatory
--           DESCRIPTION
--              "Interrupt Request level for this card/trunk. "
--
--           ::= { vStationDeviceEntry 11}

	 -- End of Device Table

	 -- The Channel Table
		
       vStationChannelTable OBJECT-TYPE
              SYNTAX  SEQUENCE OF VStationChannelEntry
              ACCESS  not-accessible
              STATUS  mandatory
              DESCRIPTION
               "Table of status, control and configuraion about
                station device channels within the system. There is
				an entry for each channel of each station device."
       ::= { vStationCardGroup 3 }

       vStationChannelEntry OBJECT-TYPE
             SYNTAX  VStationChannelEntry
             ACCESS  not-accessible
             STATUS  mandatory
             DESCRIPTION
              "An entry in the Vertical Station device Configuration
               table."
             INDEX {vStationChannelSlotNumber, vStationChannelIndex}
             ::= {vStationChannelTable 1}

	  VStationChannelEntry ::=
       SEQUENCE {
		vStationChannelIndex
            INTEGER,
		vStationChannelSlotNumber
			INTEGER,
		vStationChannelDeviceNumber
			INTEGER,
		vStationChannelChannelType
            INTEGER,
		vStationChannelMWIType
            INTEGER,
		vStationChannelOperationMode
            INTEGER,
		vStationChannelState
            INTEGER,
		vStationChannelType
            INTEGER,
		vStationChannelCallState
            INTEGER,
		vStationChannelCalledPartyNumber
			DisplayString,
		vStationChannelCallingPartyNumber
			DisplayString,
		vStationChannelChangePending
            INTEGER
}

        

    vStationChannelIndex  OBJECT-TYPE
             SYNTAX  INTEGER (1..24)
             ACCESS  read-only
             STATUS  mandatory
             DESCRIPTION
                "This is the logical channel number of the
                 channel within its station device.  
				 For 12 channel station devices, it is between 1 and 12
				 and for 24 channel stations, it is between 1 and 24."

            ::= { vStationChannelEntry 1}

	vStationChannelSlotNumber OBJECT-TYPE
             SYNTAX INTEGER (0..255)
             ACCESS  read-only
             STATUS  mandatory
             DESCRIPTION
                "The value for this object is the
                  logical number of the slot in which the 
				  card containing this channel is located (vStationDeviceSlotNumber)."

            ::= { vStationChannelEntry 2 }

	vStationChannelDeviceNumber OBJECT-TYPE
             SYNTAX INTEGER (0..255)
             ACCESS  read-only
             STATUS  mandatory
             DESCRIPTION
                "The value for this object is the logical device number of 
				 the device containing this channel within its slot, 
				 ie vStationDeviceDeviceNumber "

            ::= { vStationChannelEntry 3 }

    vStationChannelChannelType  OBJECT-TYPE                       
             SYNTAX  INTEGER {			loopStart   (1)
--						groundStart (2)
			     }		
--madhu 11 03 2000 #5450 made the access to read only				  
             ACCESS  read-only									 
             STATUS  mandatory				
             DESCRIPTION										 
                  "The Channel Type. Valid values are:
                                       1 -> loopStart"
    --                                 2 -> groundStart
            ::= { vStationChannelEntry 4}


	vStationChannelMWIType OBJECT-TYPE
             SYNTAX INTEGER { 
--							notConfigured (0),
							stutter       (1),
							lamp          (2)
			 }
             ACCESS  read-only
             STATUS  mandatory
             DESCRIPTION
                "Defines the type of Message Waiting Indication. The
				 valid values are :
				  1 -> stutter,
				  2 -> lamp."
            ::= { vStationChannelEntry 5 }
       --01 12 2001 madhu # 5455 pbx removed and notconfigured replaced with that.
    vStationChannelOperationMode  OBJECT-TYPE
             SYNTAX  INTEGER {
--					  notConfigured (0),
                      station       (1),
					  voiceMail	(2),
					  --pbx		(3)
					  notConfigured(3)
                      }
             ACCESS  read-only
             STATUS  mandatory
             DESCRIPTION
                "Defines the operation mode of the channel.
				 Valid values are :
				 1 -> station,
				 2 -> voiceMail,
				 3 -> PBX."

            ::= { vStationChannelEntry 6}
         --notConfigured commented out by madhu 11 10 2000 #5457
	vStationChannelState  OBJECT-TYPE
             SYNTAX  INTEGER {
                    disabled		 (0),
                    enabled		 (1),
		    removed		 (255)
			  --notConfigured		(2)
                   }
             ACCESS  read-only
             STATUS  mandatory
             DESCRIPTION
                "Indicates the operational status of this channel. 
				 Valid values are:
					0	 -> disabled,
					1	 -> enabled,
					255      -> currently removed as a valid station port."

            ::= { vStationChannelEntry 7}
 --madhu 11 16 2000 #5453   ; callerID_callWaiting changed to  Enhanced_CallWaiting
    vStationChannelType  OBJECT-TYPE
             SYNTAX  INTEGER {
--                    notConfigured		 (0),
                    basic				 (1),
					callerID			 (2),
--				    callerID_callWaiting (3) 
                    enhanced-CallWaiting (3)
                   }
             ACCESS  read-only
             STATUS  mandatory
             DESCRIPTION
                "The phone type for this particular channel. 
				 Valid values are:
					1 -> basic,
					2 -> callerID,
					3 -> Enhanced_CallWaiting (caller ID with call waiting). "

            ::= { vStationChannelEntry 8}


	vStationChannelCallState  OBJECT-TYPE
             SYNTAX  INTEGER {
                    call-state-VOID						(0),                
					call-state-IDLE						(1),                
					call-state-DIALING					(2),            
					call-state-COLLECT-FIRST-DIGIT		(3), 
					call-state-COLLECT-DIGITS			(4),      
					call-state-CALL-OFFERED				(5),        
					call-state-PROCEEDING				(6),          
					call-state-RINGING					(7),             
					call-state-ALERTING					(8),            
					call-state-CONNECTED				(9),           
					call-state-DISCONNECTING			(10),       
					call-state-FAILED					(11),              
					call-state-UNAVAILABLE				(12),         
					call-state-OFFHOOK					(13),             
					call-state-INITIALIZE				(14),          
					call-state-INITIALIZING				(15),        
					call-state-DIAL-REQUEST				(16),        
					call-state-HELD						(17),                
					call-state-FEATURE-INVOKED			(18),     
					call-state-OFFHOOK-IDLE				(19),        
					call-state-OFFHOOK-ACTIVE			(20),      
					call-state-OUT-OF-SERVICE			(21),      
					call-state-OUTPULSING				(22)          
                   }
             ACCESS  read-only
             STATUS  mandatory
             DESCRIPTION
                "Indicates the phone call state of this channel. 
				 Valid values are:
					call-state-VOID (0),	 -> invalid state
					call-state-IDLE (1),                -> the line is in idle state
					call-state-DIALING (2),             -> the line is originating a call
					call-state-COLLECT-FIRST-DIGIT (3), -> waiting to collect the first digit
					call-state-COLLECT-DIGITS (4),      -> collecting additional digits
					call-state-CALL-OFFERED (5),        -> the station call request has been offered to the PBX control
					call-state-PROCEEDING (6),          -> the call is in progress
					call-state-RINGING (7),             -> the call has seized a destination line
					call-state-ALERTING (8),            -> the destination has been seized
					call-state-CONNECTED (9),           -> the destination has answered the call
					call-state-DISCONNECTING (10),  -> the call is in the process of terminating
					call-state-FAILED (11),             -> the call attempt failed, wait for hangup
					call-state-UNAVAILABLE (12),        -> destination is not available to receive call
					call-state-OFFHOOK (13),            -> the call has been completed but the phone is offhook
					call-state-INITIALIZE (14),         -> initialize the call object (binds with Conn Mgr)
					call-state-INITIALIZING (15),       -> waiting for the response from Conn Mgr (Inservice Ack) 
					call-state-DIAL_REQUEST (16),       -> call object sent up OffhookInd and waiting for ACK
					call-state-HELD (17),               -> the call has been put on hold
					call-state-FEATURE-INVOKED (18),    -> indications that a feature has been invoked and waiting response
					call-state-OFFHOOK-IDLE (19),       -> indicates that the phone is set to offhook and is IDLE
					call-state-OFFHOOK-ACTIVE (20),     -> indicates that the phone is set to offhook and is ACTIVE
					call-state-OUT-OF-SERVICE (21),     -> indicates that the phone is out of service
					call-state-OUTPULSING (22),         -> digits are being sent to the external key or voice mail system"

            ::= { vStationChannelEntry 9}

	vStationChannelCalledPartyNumber  OBJECT-TYPE
			SYNTAX      DisplayString (SIZE (0..32))
			ACCESS		read-only
			STATUS      mandatory
            DESCRIPTION
                "Indicates the called party number, either an internal 
				 extension or external number."

            ::= { vStationChannelEntry 10}

	vStationChannelCallingPartyNumber  OBJECT-TYPE
			SYNTAX      DisplayString (SIZE (0..32))
			ACCESS		read-only
			STATUS      mandatory
            DESCRIPTION
                "Indicates the calling party number, either an internal 
				 extension or external number."

            ::= { vStationChannelEntry 11}

	vStationChannelChangePending  OBJECT-TYPE
             SYNTAX  INTEGER (0..1)
             ACCESS read-only
             STATUS  mandatory
             DESCRIPTION
				"Indicates that a change to the channel
				  values have been made to the registry.
				  The intepretation of the values are :
				  1 => change made to the registry, but 
				       not incorporated in the device yet
				  0 => the device changes the value to 0
				        from 1, after it incorporates the 
						value from registry."            
             ::= { vStationChannelEntry 12 }



-- The Digit Table Group

     -- Implementation of this group is mandatory for all Vertical
     -- InstantOffice systems.  
	 -- This group contains one table: The First Digit table 

     vStationDigitTableGroup
       OBJECT IDENTIFIER ::= { vStationModule 3 }


     -- The First Digit Table 
	 -- This table contain settings for each digit (0 to 9) dialed as the first digit
				
       vStationFirstDigitTable OBJECT-TYPE
              SYNTAX  SEQUENCE OF VStationFirstDigitEntry
              ACCESS  not-accessible
              STATUS  mandatory
              DESCRIPTION
               "Table of settings for each digits (0-9) which 
                may be dialled as the first digit. There are 
				10 entries, one for each digit, in this table."
       ::= { vStationDigitTableGroup 1 }

       vStationFirstDigitEntry OBJECT-TYPE
             SYNTAX  VStationFirstDigitEntry
             ACCESS  not-accessible
             STATUS  mandatory
             DESCRIPTION
              "An entry in the Vertical Station First Digit Table."
             INDEX {vStationDigitIndex}
			 ::= {vStationFirstDigitTable 1}

	  VStationFirstDigitEntry ::=
       SEQUENCE {
		vStationDigitIndex
            INTEGER,
		vStationDigitString
--			OCTET STRING,
			DisplayString,
		vStationDigitCallType
            INTEGER,
		vStationDigitMoreDigits
            INTEGER,
		--vStationDigitTimeout
          --  INTEGER,
		vStationDigitStripDigits
            INTEGER
	  }


    vStationDigitIndex  OBJECT-TYPE
             SYNTAX  INTEGER (1..10)
             ACCESS  read-only
             STATUS  mandatory
             DESCRIPTION
                "This is the index to an entry in the 
				 first digit table"
            ::= { vStationFirstDigitEntry 1}


    vStationDigitString  OBJECT-TYPE
--             SYNTAX      OCTET STRING (SIZE (1))
             SYNTAX DisplayString (SIZE (0..1))
             ACCESS  read-only
             STATUS  mandatory
             DESCRIPTION
                "The first digit string . Valid values :
				'0' to '9'"
            ::= { vStationFirstDigitEntry 2}

    vStationDigitCallType  OBJECT-TYPE
             SYNTAX  INTEGER {
						fc-VOID                           (0),  
						fc-HOLD-CALL                      (1),
						fc-PARK-CALL                      (2),
						fc-STATION-CALL                   (3),
						fc-LONG-DISTANCE-CALL             (4),
						fc-INTERNATIONAL-CALL             (5),
						fc-LOCAL-CALL                     (6),
						fc-OPERATOR-CALL                  (7),
						fc-RECEPTIONIST-CALL              (8),
						fc-CAMP-ON-CALL                   (9)
			 }
             ACCESS  read-only
             STATUS  mandatory
             DESCRIPTION
                "Type of call generated by this digit.
				 Valid values are :
						fc-VOID                           (0),       //undefined
						fc-HOLD-CALL                      (1),
						fc-PARK-CALL                      (2),
						fc-STATION-CALL                   (3),
						fc-LONG-DISTANCE-CALL             (4),
						fc-INTERNATIONAL-CALL             (5),
						fc-LOCAL-CALL                     (6),
						fc-OPERATOR-CALL                  (7),
						fc-RECEPTIONIST-CALL              (8),
						fc-CAMP-ON-CALL                   (9) "

            ::= { vStationFirstDigitEntry 3}

    vStationDigitMoreDigits  OBJECT-TYPE
             SYNTAX  INTEGER (0..32)
             ACCESS  read-only
             STATUS  mandatory
             DESCRIPTION
                "The number of additional digits to collect after the 
				 matched digits."
            ::= { vStationFirstDigitEntry 4}

   -- vStationDigitTimeout  OBJECT-TYPE
     --        SYNTAX  INTEGER {
	--					dontTerminate (0),
	--					terminate     (1)
	--		 }
      --       ACCESS  read-write
        --     STATUS  mandatory
          --   DESCRIPTION
            --    "Indicates whether the dialling should terminate on a 
			--	 timeout. valid values are :
			--	  dontTerminate -> 0
			--	  terminate		-> 1"
            --::= { vStationFirstDigitEntry 5}

    vStationDigitStripDigits  OBJECT-TYPE
             SYNTAX  INTEGER (0..32)
             ACCESS  read-only
             STATUS  mandatory
             DESCRIPTION
                "Indicates the number of leading digits to
				 strip from the digits collected before they are
				 reported up to the connection manager."
            ::= { vStationFirstDigitEntry 6}




	 --   The External Voice 
	 --       Mail System Group:  This group contains configuration information used 
	 --                           to interface with an external voice mail system. 
	 --							  This group is subdivided into subgroups depending 
	 --							  on the type of the voice mail system used. Currently,
	 --							  there is just one subgroup: the ATT_System_25 subgroup.



-- The External VoiceMail  Group

     -- Implementation of this group is mandatory for all Vertical
     -- InstantOffice systems.  
	 -- This group contains configuration information used 
	 -- to interface with an external voice mail system. 
	 --	This group is subdivided into subgroups depending 
	 --	on the type of the voice mail system used. Currently,
	 --	there is just one subgroup: the ATT_System_25 subgroup.

     vStationExtVoiceMailGroup
       OBJECT IDENTIFIER ::= { vStationModule 4 }


     -- The ATTSystem25 subgroup 
	 -- conatins one table The Voice Mail Call Handle table

	vStationATTSystem25Group
	   OBJECT IDENTIFIER ::= { vStationExtVoiceMailGroup 1 }
		
    vStationMWILampON OBJECT-TYPE
             SYNTAX  DisplayString (SIZE (0..10))
             ACCESS  read-only
             STATUS  mandatory
             DESCRIPTION
                "Command expected from the external voice mail
				 system to turn on a station's lamp."
            ::= { vStationATTSystem25Group 1 }

    vStationMWILampOFF OBJECT-TYPE
             SYNTAX  DisplayString (SIZE (0..10))
             ACCESS  read-only
             STATUS  mandatory
             DESCRIPTION
                "Command expected from the external voice mail
				 system to turn off a station's lamp."
            ::= { vStationATTSystem25Group 2 }

	-- The Voice Mail call Handle table

	vStationVMCallHandleTable OBJECT-TYPE
              SYNTAX  SEQUENCE OF VStationVMCallHandleEntry
              ACCESS  not-accessible
              STATUS  mandatory
              DESCRIPTION
               "Table of settings and commands for accessing the 
			    voice mail port for different types of access, 
				i.e. external caller coming directly to voice mail port,
				external caller being forwarded to a voice mail port, etc."
       ::= { vStationATTSystem25Group 3 }


       vStationVMCallHandleEntry OBJECT-TYPE
             SYNTAX  VStationVMCallHandleEntry
             ACCESS  not-accessible
             STATUS  mandatory
             DESCRIPTION
              "An entry in the Vertical Station Voice Mail call handle table."
             INDEX {vStationVMCallHandleIndex}
			 ::= {vStationVMCallHandleTable 1}


	  VStationVMCallHandleEntry ::=
			SEQUENCE {
				vStationVMCallHandleIndex
					INTEGER,
				vStationVMCallHandleType
					INTEGER,
				vStationVMCallHandleOpcode
					OCTET STRING,
				vStationVMCallHandleSRCNumber
					OCTET STRING,
				vStationVMCallHandleDSTNumber
					OCTET STRING
			}


    vStationVMCallHandleIndex  OBJECT-TYPE
             SYNTAX  INTEGER (1..10)
             ACCESS  read-only
             STATUS  mandatory
             DESCRIPTION
                "This is the index to an entry in the 
				 Voice Mail call handle table."
            ::= { vStationVMCallHandleEntry 1}

    vStationVMCallHandleType  OBJECT-TYPE
             SYNTAX  INTEGER {
					directExternal  (1),
					forwardExternal (2),
					directInternal  (3),
					forwardInternal (4)
			 }
             ACCESS  read-only
             STATUS  mandatory
             DESCRIPTION
                "Indicates the type of access to voice mail port made.
				 valid values are :
				 directExternal  (1) -> An external caller coming directly into the 
				                        voice mail port.
				 forwardExternal (2) -> An external caller caling an extension, but 
				                        was then forwarded to the voice mail port.
				 directInternal  (3) -> An internal caller coming directly into the 
										voice mail port.
				 forwardInternal (4) -> An internal caller caling an extension, but 
				                        was then forwarded to the voice mail port."
            ::= { vStationVMCallHandleEntry 2}


    vStationVMCallHandleOpcode  OBJECT-TYPE
             SYNTAX      OCTET STRING (SIZE (0..32))
             ACCESS  read-only
             STATUS  mandatory
             DESCRIPTION
                "The opcode string for this operation."
            ::= { vStationVMCallHandleEntry 3}

    vStationVMCallHandleSRCNumber  OBJECT-TYPE
             SYNTAX      OCTET STRING (SIZE (0..32))
             ACCESS  read-only
             STATUS  mandatory
             DESCRIPTION
                "The source number format string. It contains
				 a C type '%s' where the source number would
				 be filled in"
            ::= { vStationVMCallHandleEntry 4}

    vStationVMCallHandleDSTNumber  OBJECT-TYPE
             SYNTAX      OCTET STRING (SIZE (0..32))
             ACCESS  read-only
             STATUS  mandatory
             DESCRIPTION
                "The destination number format string. It contains
				 a C type '%s' where the destination number would
				 be filled in"
            ::= { vStationVMCallHandleEntry 5}


-- TRAP Definitions - TO BE RESOLVED

vStationCannotPlayTone TRAP-TYPE
	ENTERPRISE  vertical
	VARIABLES {vStationChannelSlotNumber, vStationChannelDeviceNumber ,vStationChannelIndex }
	DESCRIPTION
        " This notification is sent when the specific
          channel cannot play tone. "
	::= 12

vStationCannotCancelTone TRAP-TYPE
	ENTERPRISE  vertical
	VARIABLES {vStationChannelSlotNumber, vStationChannelDeviceNumber ,vStationChannelIndex }
	DESCRIPTION
        " This notification is sent when the specific
          channel cannot cancel tone. "
	::= 13

vStationCannotAttachDigitCollector TRAP-TYPE
	ENTERPRISE  vertical
	VARIABLES {vStationChannelSlotNumber, vStationChannelDeviceNumber ,vStationChannelIndex }
	DESCRIPTION
        " This notification is sent when the specific
          channel cannot attach digits collected "
	::= 14

vStationCannotReleaseDigitCollector TRAP-TYPE
	ENTERPRISE  vertical
	VARIABLES {vStationChannelSlotNumber, vStationChannelDeviceNumber ,vStationChannelIndex }
	DESCRIPTION
        " This notification is sent when the specific
          channel cannot release digits collected "
	::= 15

vStationRECONFIG-COMPLETE TRAP-TYPE
	ENTERPRISE  vertical
	VARIABLES {vStationChannelSlotNumber, vStationChannelDeviceNumber }
	DESCRIPTION
        " This notification is sent when the specific
          station device successfully reads and incorporates the
		  values from the registry."
	::= 16

vStationRECONFIG-ERROR TRAP-TYPE
	ENTERPRISE  vertical
	VARIABLES {vStationChannelSlotNumber, vStationChannelDeviceNumber }
	DESCRIPTION
        " This notification is sent when the specific
          station device fails to incorporate the values read from
		  the registry. "
	::= 17


END
